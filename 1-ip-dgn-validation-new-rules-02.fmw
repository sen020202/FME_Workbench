FME workspace 1-ip-dgn-validation-new-rules-02.fmw

Parameters:
- DestDataset_DGNV8 =
- FEATURE_TYPES =
- FEATURE_TYPES_2 =
- SourceDataset_DGNV8 =
- SourceDataset_XLSXR =

Readers:
- DGNV8_1: DGNV8 from $(SourceDataset_DGNV8)
- XLSXR_1: XLSXR from $(SourceDataset_XLSXR)

Writers:
- DGNV8_2: DGNV8 to $(DestDataset_DGNV8)

05007_Sports_Footbal_Shp (reader DGNV8_1)
    -> Counter
Counter
    CNT_ATTR = _count
    DOMAIN = counter
    SCOPE = Global
    START = 1
    -> FeatureJoiner [LEFT]
Rules (reader XLSXR_1)
    attributes: Level_name char(63), Test_Name char(21), Sub-group_Test char(42), Axis/EDGE/Poly char(18)
    -> FeatureJoiner [RIGHT]
FeatureJoiner
    ATTR_CONFLICT_RES = Use Left
    GEOMETRY_HANDLING = Use Left
    JOIN_KEYS = igds_level_name Level_name AUTO
    JOIN_MODE = Inner
    JOINED -> Tester
    JOINED -> Tester_7
    JOINED -> Tester_22
    JOINED -> Tester_24
    JOINED -> Tester_16
    JOINED -> Tester_67
    JOINED -> Tester_77
    UNJOINED_LEFT -> Tester_8
Tester_8
    BOOL_OP = OR
    COMPOSITE_TEST = 1
    TEST_CLAUSE = TEST @Value(igds_level_name) = REF_12000_Boundary_0_Ln
    TEST_MODE = TEST
    PASSED -> GeometryCoercer_2
05007_Sports_Footbal_Shp (writer DGNV8_2)

Bookmark: VAD_CHECK
Tester_7
    BOOL_OP = OR
    COMPOSITE_TEST = 1
    TEST_CLAUSE = TEST @Value(Test_Name) = VAD_Check
    TEST_MODE = TEST
    PASSED -> Tester_10
    PASSED -> Tester_14
    FAILED -> Tester_19
Note: VAD_CHECK
Tester_10
    BOOL_OP = OR
    COMPOSITE_TEST = 1 OR 2
    TEST_CLAUSE:
      TEST @Value(Axis/EDGE/Poly) = VAD_Axis
      TEST @Value(Axis/EDGE/Poly) = VAD_Poly
    TEST_MODE = TEST
    PASSED -> Tester_11
    FAILED -> Tester_63
Tester_11
    BOOL_OP = OR
    COMPOSITE_TEST = 1
    TEST_CLAUSE = TEST @Value(Axis/EDGE/Poly) = VAD_Axis
    TEST_MODE = TEST
    PASSED -> LineCombiner_2
    FAILED -> Tester_70 [off]
    FAILED -> GeometryFilter_2
LineCombiner_2
    ACCUM_ATTRS_NAME = Use Attributes From One Feature
    BREAK = no
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    PRESERVE = no
    TOPOLOGY = End noded
    LINE -> Intersector
Tester_70 [off]
    BOOL_OP = OR
    COMPOSITE_TEST = 1
    TEST_CLAUSE = TEST @Value(Axis/EDGE/Poly) = VAD_Poly
    TEST_MODE = TEST
    PASSED -> LineCombiner_17 [off]
LineCombiner_17 [off]
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> GeometryCoercer_4 [off]
GeometryCoercer_4 [off]
    GQUERY:
      for $geom in //geometry
      where $geom/count(parent::geometry) = 0
      return number($geom/@fme_id)
    KIND = fme_polygon
    COERCED -> GeometryFilter_2 [off]
    UNTOUCHED -> AttributeCreator_3
GeometryFilter_2
    BREAK_AGG = No
    GEOM_PORT_NAMES = Area
    <UNFILTERED> -> AttributeCreator_3
    AREA -> Intersector
    AREA -> SpatialFilter [Candidate]
    AREA -> SpatialFilter_2 [Filter]
Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Tester_12
Tester_12
    BOOL_OP = OR
    COMPOSITE_TEST = 1
    TEST_CLAUSE = TEST @Value(Axis/EDGE/Poly) = VAD_Axis
    TEST_MODE = TEST
    PASSED -> Snipper
Snipper
    DEAGGREGATE_INPUT = YES
    ENDLOCATIONATTR = 99.5
    MEASUREMENTTYPE = 2D
    SNIPMODE = Distance (Percentage)
    STARTLOCATIONATTR = 0.5
    -> SpatialFilter [Filter]
    -> SpatialFilter_2 [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN
    USE_BOUNDING_BOX = No
    FAILED -> AttributeCreator_4
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    FAILED -> AttributeCreator_4
AttributeCreator_4
    ATTR_TABLE = SET_TO igds_level_name = Err_VAD_POLY_Lines_@Value(Sub-group_Test)
    -> Junction_3
Tester_63
    BOOL_OP = OR
    COMPOSITE_TEST = 1 OR 2
    TEST_CLAUSE:
      TEST @Value(Axis/EDGE/Poly) = LINEAR-Axis
      TEST @Value(Axis/EDGE/Poly) = LINEAR-VAD
    TEST_MODE = TEST
    PASSED -> Tester_64
Tester_64
    BOOL_OP = OR
    COMPOSITE_TEST = 1
    TEST_CLAUSE = TEST @Value(Axis/EDGE/Poly) = LINEAR-Axis
    TEST_MODE = TEST
    PASSED -> LineCombiner_9
    FAILED -> LineCombiner_10
LineCombiner_9
    ACCUM_ATTRS_NAME = Use Attributes From One Feature
    BREAK = no
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    PRESERVE = no
    TOPOLOGY = End noded
    LINE -> SpatialFilter_7 [Filter]
LineCombiner_10
    ACCUM_ATTRS_NAME = Use Attributes From One Feature
    BREAK = no
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    PRESERVE = no
    TOPOLOGY = End noded
    LINE -> SpatialFilter_7 [Candidate]
    <REJECTED> -> AttributeCreator_3
SpatialFilter_7
    AGGREGATE_HANDLING = Yes
    ATTR_ACCUM_MODE = Merge Filter
    ATTR_CONFLICT_RES = Use Candidate
    BASE_TYPE = Multiple Filters
    CURVE_BOUNDARY_RULE_PARAM = Default Rule
    GROUP_BY = Sub-group_Test
    PASS_CRITERIA = Pass Against One Filter
    PREDATTR = _predicate
    PREDICATES = INTERSECTS TOUCHES
    USE_BOUNDING_BOX = No
    FAILED -> AttributeCreator_22
Tester_14
    BOOL_OP = OR
    COMPOSITE_TEST = 1 OR 2
    TEST_CLAUSE:
      TEST @Value(Axis/EDGE/Poly) = VAD_Poly
      TEST @Value(Axis/EDGE/Poly) = Axis
    TEST_MODE = TEST
    PASSED -> Tester_13
Tester_13
    BOOL_OP = OR
    COMPOSITE_TEST = 1
    TEST_CLAUSE = TEST @Value(Axis/EDGE/Poly) = VAD_Poly
    TEST_MODE = TEST
    PASSED -> Tester_73 [off]
    PASSED -> GeometryFilter_3
    FAILED -> LineCombiner_4
LineCombiner_4
    ACCUM_ATTRS_NAME = Use Attributes From One Feature
    BREAK = no
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    PRESERVE = no
    TOPOLOGY = End noded
    LINE -> Intersector_3
    <REJECTED> -> AttributeCreator_22
AttributeCreator_22
    ATTR_TABLE = SET_TO igds_level_name = Err_VAD_Track_Lines_@Value(Sub-group_Test)
    -> Junction_3
Tester_73 [off]
    BOOL_OP = OR
    COMPOSITE_TEST = 1
    TEST_CLAUSE = TEST @Value(Axis/EDGE/Poly) = VAD_Poly
    TEST_MODE = TEST
    PASSED -> LineCombiner_18 [off]
LineCombiner_18 [off]
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> GeometryCoercer_5 [off]
GeometryCoercer_5 [off]
    GQUERY:
      for $geom in //geometry
      where $geom/count(parent::geometry) = 0
      return number($geom/@fme_id)
    KIND = fme_polygon
    COERCED -> GeometryFilter_3 [off]
    UNTOUCHED -> AttributeCreator_3
GeometryFilter_3
    BREAK_AGG = No
    GEOM_PORT_NAMES = Area
    AREA -> Intersector_3
    AREA -> SpatialFilter_8 [Candidate]
    AREA -> SpatialFilter_9 [Filter]
    <UNFILTERED> -> AttributeCreator_3
Intersector_3
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Tester_15
Tester_15
    BOOL_OP = OR
    COMPOSITE_TEST = 1
    TEST_CLAUSE = TEST @Value(Axis/EDGE/Poly) = Axis
    TEST_MODE = TEST
    PASSED -> Snipper_4
Snipper_4
    DEAGGREGATE_INPUT = YES
    ENDLOCATIONATTR = 99.5
    MEASUREMENTTYPE = 2D
    SNIPMODE = Distance (Percentage)
    STARTLOCATIONATTR = 0.5
    -> SpatialFilter_8 [Filter]
    -> SpatialFilter_9 [Candidate]
SpatialFilter_8
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_5
SpatialFilter_9
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> AttributeCreator_5
AttributeCreator_5
    ATTR_TABLE = SET_TO igds_level_name = Err_VAD_POLY_Lines_@Value(Sub-group_Test)
    -> Junction_3
AttributeCreator_3
    ATTR_TABLE = SET_TO igds_level_name = Err_Wrong_Geometry_@Value(Sub-group_Test)
    -> Junction_3
Junction_3
    -> Inspector_3
    -> 05007_Sports_Footbal_Shp (writer DGNV8_2)
Inspector_3

Bookmark: ELE_VAD
Tester_19
    BOOL_OP = OR
    COMPOSITE_TEST = 1
    TEST_CLAUSE = TEST @Value(Test_Name) = ELE_Check
    TEST_MODE = TEST
    PASSED -> Tester_29
Tester_29
    BOOL_OP = OR
    COMPOSITE_TEST = 1
    TEST_CLAUSE = TEST @Value(Axis/EDGE/Poly) = ELE_Axis
    TEST_MODE = TEST
    PASSED -> LineCombiner_7
    FAILED -> Tester_30
    FAILED -> Tester_40
Tester_40
    BOOL_OP = OR
    COMPOSITE_TEST = 1
    TEST_CLAUSE = TEST @Value(Axis/EDGE/Poly) = ELE_Poly
    TEST_MODE = TEST
    PASSED -> Bufferer_5
    FAILED -> Tester_41
Note: ELE_CHK
Tester_41
    BOOL_OP = OR
    COMPOSITE_TEST = 1
    TEST_CLAUSE = TEST @Value(Axis/EDGE/Poly) = Poly
    TEST_MODE = TEST
    PASSED -> Bufferer_6
Bufferer_6
    ANGLE = 22.5
    CAP_STYLE = Arc
    CORNER_STYLE = Arc
    MODE = AREA
    OFFSET = 0.5
    OFFSET_UNITS = NONE
    PRECISION = APPROX
    BUFFERED -> SpatialRelator_3 [Supplier]
Bufferer_5
    ANGLE = 22.5
    CAP_STYLE = Arc
    CORNER_STYLE = Arc
    MODE = AREA
    OFFSET = 0.5
    OFFSET_UNITS = NONE
    PRECISION = APPROX
    BUFFERED -> SpatialRelator_3 [Requestor]
SpatialRelator_3
    AGGREGATE_HANDLING = Yes
    CALC_CARD = No
    CURVE_BOUNDARY_RULE_PARAM = Default Rule
    GROUP_BY = Sub-group_Test
    LIST_NAME = _relationships
    PREDICATES = INTERSECTS
    SUCCESS_ATTR = _related_suppliers
    -> Tester_42
Tester_42
    BOOL_OP = OR
    COMPOSITE_TEST = 1
    TEST_CLAUSE = TEST @Value(_related_suppliers) = 1
    TEST_MODE = TEST
    PASSED -> AttributeCreator_7
    FAILED -> Tester_21
Tester_21
    BOOL_OP = OR
    COMPOSITE_TEST = 1 OR 2
    TEST_CLAUSE:
      TEST @Value(_related_suppliers) = 2
      TEST @Value(_related_suppliers) = 3
    TEST_MODE = TEST
    FAILED -> AttributeCreator_14
AttributeCreator_14
    ATTR_TABLE = SET_TO igds_level_name = CHK_Err_No_poly-lines_@Value(Sub-group_Test)_@Value(_related_suppliers)
    -> Junction_4
AttributeCreator_7
    ATTR_TABLE = SET_TO igds_level_name = CHK_Err_1_Edge_Poly_@Value(Sub-group_Test)_@Value(_related_suppliers)
    -> Junction_4
LineCombiner_7
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Snipper_3
    LINE -> CoordinateExtractor_5
    LINE -> CoordinateExtractor_6
CoordinateExtractor_5
    IND = 0
    MODE = Specify Coordinate
    X_ATTR = _x
    Y_ATTR = _y
    Z_ATTR = _z
    -> VertexCreator_5
VertexCreator_5
    MEASURE_TYPE = Continuous
    MODE_NAME = Replace with Point
    XVAL = @Value(_x)
    YVAL = @Value(_y)
    ZVAL = @Value(_z)
    -> PointOnLineOverlayer_3 [POINT]
CoordinateExtractor_6
    IND = -1
    MODE = Specify Coordinate
    X_ATTR = _x
    Y_ATTR = _y
    Z_ATTR = _z
    -> VertexCreator_6
VertexCreator_6
    MEASURE_TYPE = Continuous
    MODE_NAME = Replace with Point
    XVAL = @Value(_x)
    YVAL = @Value(_y)
    ZVAL = @Value(_z)
    -> PointOnLineOverlayer_3 [POINT]
Snipper_3
    DEAGGREGATE_INPUT = YES
    ENDLOCATIONATTR = 99
    MEASUREMENTTYPE = 2D
    SNIPMODE = Distance (Percentage)
    STARTLOCATIONATTR = 1
    -> Intersector_4
Tester_30
    BOOL_OP = OR
    COMPOSITE_TEST = 1
    TEST_CLAUSE = TEST @Value(Axis/EDGE/Poly) = ELE_Poly
    TEST_MODE = TEST
    PASSED -> LineOnAreaOverlayer_3 [AREA]
    PASSED -> Intersector_4
    PASSED -> GeometryCoercer_3
GeometryCoercer_3
    GQUERY:
      for $geom in //geometry
      where $geom/count(parent::geometry) = 0
      return number($geom/@fme_id)
    KIND = fme_line
    COERCED -> PointOnLineOverlayer_3 [LINE]
PointOnLineOverlayer_3
    DEAGGREGATE_INPUT = Yes
    MEASURE_TYPE = Continuous
    MERGE_MEASURES = Yes
    OV_ATTR = _overlaps
    TOLERANCE = 0.1
    POINT -> Tester_38
    LINE -> Tester_39
Tester_38
    BOOL_OP = OR
    COMPOSITE_TEST = 1
    TEST_CLAUSE = TEST @Value(_overlaps) = 1
    TEST_MODE = TEST
    FAILED -> AttributeCreator_13
Tester_39
    BOOL_OP = OR
    COMPOSITE_TEST = 1
    TEST_CLAUSE = TEST @Value(_overlaps) = 2
    TEST_MODE = TEST
    FAILED -> AttributeCreator_13
AttributeCreator_13
    ATTR_TABLE = SET_TO igds_level_name = Err_No_poly-lines_@Value(Sub-group_Test)_@Value(_overlaps)
    -> Junction_4
Intersector_4
    ATTRS_ACCUM_MODE = Use Attributes From One Feature
    CLEANING_TOLERANCE = 0.001
    DEAGGREGATE_INPUT = Yes
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Tester_35
    COLLAPSED -> AttributeCreator_11
Tester_35
    BOOL_OP = OR
    COMPOSITE_TEST = 1
    TEST_CLAUSE = TEST @Value(Axis/EDGE/Poly) = ELE_Axis
    TEST_MODE = TEST
    PASSED -> LineOnAreaOverlayer_3 [LINE]
LineOnAreaOverlayer_3
    CLEANING_TOLERANCE = 0.01
    DEAGGREGATE_INPUT = Yes
    OV_ATTR = _overlaps
    LINE -> Tester_36
    AREA -> Tester_37
Tester_36
    BOOL_OP = OR
    COMPOSITE_TEST = 1
    TEST_CLAUSE = TEST @Value(_overlaps) = 1
    TEST_MODE = TEST
    FAILED -> AttributeCreator_12
Tester_37
    BOOL_OP = OR
    COMPOSITE_TEST = 1
    TEST_CLAUSE = TEST @Value(_overlaps) = 1
    TEST_MODE = TEST
    FAILED -> AttributeCreator_12
AttributeCreator_12
    ATTR_TABLE = SET_TO igds_level_name = Err_No_poly-lines_@Value(Sub-group_Test)_@Value(_overlaps)
    -> Junction_4
AttributeCreator_11
    ATTR_TABLE = SET_TO igds_level_name = Err_wrong_Geometry_@Value(Sub-group_Test)
    -> Junction_4
Junction_4
    -> Inspector_5
    -> 05007_Sports_Footbal_Shp (writer DGNV8_2)
Inspector_5

Bookmark: LINE_POLY-CHECK
GeometryCoercer_2
    GQUERY:
      for $geom in //geometry
      where $geom/count(parent::geometry) = 0
      return number($geom/@fme_id)
    KIND = fme_polygon
    COERCED -> LineOnAreaOverlayer_2 [AREA]
Tester_3
    BOOL_OP = OR
    COMPOSITE_TEST = 1
    TEST_CLAUSE = TEST @Value(Test_Name) = Line-Poly_Check
    TEST_MODE = TEST
    PASSED -> Intersector_2
    PASSED -> Tester_5
Note: LINE_POLY-CHECK
Tester_5
    BOOL_OP = OR
    COMPOSITE_TEST = 1
    TEST_CLAUSE = TEST @Value(Axis/EDGE/Poly) = Edge
    TEST_MODE = TEST
    PASSED -> GeometryCoercer
    FAILED -> LineOnAreaOverlayer [AREA]
GeometryCoercer
    GQUERY:
      for $geom in //geometry
      where $geom/count(parent::geometry) = 0
      return number($geom/@fme_id)
    KIND = fme_line
    COERCED -> LineOnAreaOverlayer [LINE]
LineOnAreaOverlayer
    CLEANING_TOLERANCE = 0.001
    DEAGGREGATE_INPUT = Yes
    GROUP_BY = Sub-group_Test
    OV_ATTR = _overlaps
    LINE -> Tester_6
Tester_6
    BOOL_OP = OR
    COMPOSITE_TEST = 1 OR 2
    TEST_CLAUSE:
      TEST @Value(_overlaps) = 0
      TEST @Value(_overlaps) = 3
    TEST_MODE = TEST
    PASSED -> AttributeCreator_2
Intersector_2
    ATTRS_ACCUM_MODE = Use Attributes From One Feature
    CLEANING_TOLERANCE = 0.001
    DEAGGREGATE_INPUT = Yes
    DUPLICATE_Z_NODES = No
    GENERATE_LIST_DROP = NO
    GRP_BY = Sub-group_Test
    MEASURE_TYPE = Continuous
    NODE_NUM_ATTR = _node_number
    OV_ATTR = _overlaps
    SEG_ATTR = _segments
    SEPARATE_COLLINEAR_SEGMENTS = No
    INTERSECTED -> Tester_4
Tester_4
    BOOL_OP = OR
    COMPOSITE_TEST = 1
    TEST_CLAUSE = TEST @Value(_overlaps) = 2
    TEST_MODE = TEST
    FAILED -> LineOnAreaOverlayer_2 [LINE]
LineOnAreaOverlayer_2
    CLEANING_TOLERANCE = 0.01
    DEAGGREGATE_INPUT = Yes
    OV_ATTR = _overlaps
    LINE -> Tester_9
Tester_9
    BOOL_OP = OR
    COMPOSITE_TEST = 1
    TEST_CLAUSE = TEST @Value(_overlaps) = 1
    TEST_MODE = TEST
    PASSED -> AttributeCreator_2
AttributeCreator_2
    ATTR_TABLE = SET_TO igds_level_name = Err_NO_Original_Lines_@Value(Sub-group_Test)
    -> Junction_2
Junction_2
    -> Inspector_2
    -> 05007_Sports_Footbal_Shp (writer DGNV8_2)
Inspector_2

Bookmark: Bridge_Test
Tester_22
    BOOL_OP = OR
    COMPOSITE_TEST = 1
    TEST_CLAUSE = TEST @Value(Test_Name) = Bridge_Test
    TEST_MODE = TEST
    PASSED -> GeometryFilter
GeometryFilter
    BREAK_AGG = No
    GEOM_PORT_NAMES = Line Area
    LINE -> LineOnAreaOverlayer_4 [LINE]
    AREA -> LineOnAreaOverlayer_4 [AREA]
LineOnAreaOverlayer_4
    ATTR_ACCUM_MODE = Merge Incoming
    ATTR_CONFLICT_RES = Use Original
    CANDIDATE_LIST_ATTRS_TO_INCLUDE_MODE = Selected Attributes
    CLEANING_TOLERANCE = Automatic
    DEAGGREGATE_INPUT = Yes
    OV_ATTR = _overlaps
    AREA -> Tester_23
Tester_23
    BOOL_OP = OR
    COMPOSITE_TEST = 1
    TEST_CLAUSE = TEST @Value(_overlaps) = 0
    TEST_MODE = TEST
    FAILED -> AttributeCreator_9
Note: Bridge_Test
AttributeCreator_9
    ATTR_TABLE = SET_TO igds_level_name = Err_Bridge_Line_POLY_There_@Value(Sub-group_Test)
    -> Inspector_4
    -> 05007_Sports_Footbal_Shp (writer DGNV8_2)
Inspector_4

Bookmark: AXIS_Check
Note: AXIS_Check
Tester
    BOOL_OP = OR
    COMPOSITE_TEST = 1
    TEST_CLAUSE = TEST @Value(Test_Name) = Axis-Poly Check
    TEST_MODE = TEST
    PASSED -> Tester_2
    FAILED -> Tester_3
Tester_2
    BOOL_OP = OR
    COMPOSITE_TEST = 1
    TEST_CLAUSE = TEST @Value(Sub-group_Test) = urban_Test
    TEST_MODE = TEST
    FAILED -> Tester_31
Tester_31
    BOOL_OP = OR
    COMPOSITE_TEST = 1
    TEST_CLAUSE = TEST @Value(Axis/EDGE/Poly) = Poly
    TEST_MODE = TEST
    PASSED -> GeometryFilter_10
    FAILED -> Tester_32
GeometryFilter_10
    BREAK_AGG = No
    GEOM_PORT_NAMES = Line Area
    AREA -> Intersector_6
    AREA -> SpatialFilter_11 [Filter]
    AREA -> SpatialFilter_10 [Candidate]
Tester_32
    BOOL_OP = OR
    COMPOSITE_TEST = 1 OR 2
    TEST_CLAUSE:
      TEST @Value(Axis/EDGE/Poly) = Axis
      TEST @Value(Axis/EDGE/Poly) = Edge
    TEST_MODE = TEST
    PASSED -> GeometryFilter_11
GeometryFilter_11
    BREAK_AGG = No
    GEOM_PORT_NAMES = Line Area
    LINE -> LineCombiner_6
    <UNFILTERED> -> AttributeCreator_19
LineCombiner_6
    ACCUM_ATTRS_NAME = Use Attributes From One Feature
    BREAK = no
    BREAK_CONNECTION_ATTRIBUTES = Axis/EDGE/Poly igds_level_name Sub-group_Test
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Intersector_6
Intersector_6
    ATTRS_ACCUM_MODE = Use Attributes From One Feature
    CLEANING_TOLERANCE = 0.001
    DEAGGREGATE_INPUT = Yes
    DUPLICATE_Z_NODES = No
    GENERATE_LIST_DROP = NO
    GRP_BY = Sub-group_Test
    MEASURE_TYPE = Continuous
    NODE_NUM_ATTR = _node_number
    OV_ATTR = _overlaps
    SEG_ATTR = _segments
    SEPARATE_COLLINEAR_SEGMENTS = No
    INTERSECTED -> Tester_33
Tester_33
    BOOL_OP = OR
    COMPOSITE_TEST = 1
    TEST_CLAUSE = TEST @Value(Axis/EDGE/Poly) = Poly
    TEST_MODE = TEST
    PASSED -> LineCombiner
    FAILED -> SpatialFilter_11 [Candidate]
    FAILED -> SpatialFilter_10 [Filter]
SpatialFilter_10
    AGGREGATE_HANDLING = Yes
    ATTR_ACCUM_MODE = Merge Filter
    ATTR_CONFLICT_RES = Use Candidate
    BASE_TYPE = Multiple Filters
    CURVE_BOUNDARY_RULE_PARAM = Default Rule
    GROUP_BY = Sub-group_Test
    PASS_CRITERIA = Pass Against One Filter
    PREDATTR = _predicate
    PREDICATES = INTERSECTS
    USE_BOUNDING_BOX = No
    FAILED -> AttributeCreator_20
SpatialFilter_11
    AGGREGATE_HANDLING = Yes
    ATTR_ACCUM_MODE = Merge Filter
    ATTR_CONFLICT_RES = Use Candidate
    BASE_TYPE = Multiple Filters
    CURVE_BOUNDARY_RULE_PARAM = Default Rule
    GROUP_BY = Sub-group_Test
    PASS_CRITERIA = Pass Against One Filter
    PREDATTR = _predicate
    PREDICATES = INTERSECTS
    USE_BOUNDING_BOX = No
    FAILED -> AttributeCreator_20
AttributeCreator_20
    ATTR_TABLE = SET_TO igds_level_name = Err_NO_Poly_Or_AXIS_LINE_@Value(Sub-group_Test)
    -> Junction
LineCombiner
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> LengthCalculator_5
LengthCalculator_5
    DIM = 2
    LEN_ATTR = _length
    MULT = 1
    -> Tester_34
Tester_34
    BOOL_OP = OR
    COMPOSITE_TEST = 1
    TEST_CLAUSE = TEST @Value(_length) <= 20
    TEST_MODE = TEST
    FAILED -> AttributeCreator_19
AttributeCreator_19
    ATTR_TABLE = SET_TO igds_level_name = Err_NO_Original_Lines_@Value(Sub-group_Test)
    -> Junction
Junction
    -> Inspector
    -> 05007_Sports_Footbal_Shp (writer DGNV8_2)
Inspector

Bookmark: CNX-CHeck
Tester_24
    BOOL_OP = OR
    COMPOSITE_TEST = 1
    TEST_CLAUSE = TEST @Value(Test_Name) = TRACK_CNX_TEST
    TEST_MODE = TEST
    PASSED -> Tester_25
    PASSED -> Tester_28
Tester_25
    BOOL_OP = OR
    COMPOSITE_TEST = 1
    TEST_CLAUSE = TEST @Value(Axis/EDGE/Poly) = Poly
    TEST_MODE = TEST
    PASSED -> SpatialFilter_4 [Filter]
    PASSED -> SpatialFilter_5 [Filter]
    FAILED -> Tester_26
Tester_26
    BOOL_OP = OR
    COMPOSITE_TEST = 1
    TEST_CLAUSE = TEST @Value(Axis/EDGE/Poly) = Linear-AXIS-Line
    TEST_MODE = TEST
    FAILED -> Tester_27
Note: CNX-Check
Tester_27
    BOOL_OP = OR
    COMPOSITE_TEST = 1
    TEST_CLAUSE = TEST @Value(Axis/EDGE/Poly) = CNX
    TEST_MODE = TEST
    PASSED -> SpatialFilter_4 [Candidate]
    FAILED -> Tester_50
SpatialFilter_4
    AGGREGATE_HANDLING = Yes
    BASE_TYPE = Multiple Filters
    CURVE_BOUNDARY_RULE_PARAM = Default Rule
    GROUP_BY = Sub-group_Test
    PASS_CRITERIA = Pass Against One Filter
    PREDATTR = _predicate
    PREDICATES = INTERSECTS
    USE_BOUNDING_BOX = No
    FAILED -> SpatialFilter_5 [Candidate]
SpatialFilter_5
    AGGREGATE_HANDLING = Yes
    ATTR_ACCUM_MODE = Prefix Filter
    ATTR_PREFIX = _NX_
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_17
    FAILED -> AttributeCreator_16
AttributeCreator_17
    ATTR_TABLE = SET_TO igds_level_name = CHK_CNX_OTH-RD_POLY_@Value(Sub-group_Test)
    -> Junction_5
AttributeCreator_16
    ATTR_TABLE = SET_TO igds_level_name = Err_CNX_Outside-RD_POLY_@Value(Sub-group_Test)
    -> Junction_5
Tester_50
    BOOL_OP = OR
    COMPOSITE_TEST = 1
    TEST_CLAUSE = TEST @Value(Axis/EDGE/Poly) = Track_CNX
    TEST_MODE = TEST
    PASSED -> LineCombiner_5
    FAILED -> Tester_57
LineCombiner_5
    ACCUM_ATTRS_NAME = Use Attributes From One Feature
    BREAK = no
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    PRESERVE = no
    TOPOLOGY = End noded
    LINE -> SpatialFilter_3 [Candidate]
Tester_57
    BOOL_OP = OR
    COMPOSITE_TEST = 1
    TEST_CLAUSE = TEST @Value(Axis/EDGE/Poly) = Track_Linear
    TEST_MODE = TEST
    PASSED -> LineCombiner_8
LineCombiner_8
    ACCUM_ATTRS_NAME = Use Attributes From One Feature
    BREAK = no
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    PRESERVE = no
    TOPOLOGY = End noded
    LINE -> SpatialFilter_3 [Filter]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    FAILED -> AttributeCreator_18
AttributeCreator_18
    ATTR_TABLE = SET_TO igds_level_name = Err_CNX_Track_@Value(Sub-group_Test)
    -> Junction_5
Tester_28
    BOOL_OP = OR
    COMPOSITE_TEST = 1
    TEST_CLAUSE = TEST @Value(Test_Name) = TRACK_CNX_TEST
    TEST_MODE = TEST
    PASSED -> LineCombiner_3
    PASSED -> Tester_56
    PASSED -> Tester_58
    PASSED -> Tester_59
LineCombiner_3
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Tester_43
    <REJECTED> -> AttributeCreator_10
AttributeCreator_10
    ATTR_TABLE = SET_TO igds_level_name = Err_CNX_Wrong_Geometry_@Value(Sub-group_Test)
    -> Junction_5
Tester_43
    BOOL_OP = OR
    COMPOSITE_TEST = 1
    TEST_CLAUSE = TEST @Value(igds_level_name) = REF_3001_RD_Axis_UnPaved_GRD_Ln
    TEST_MODE = TEST
    PASSED -> NodeValence_2 [Line]
    FAILED -> Tester_44
NodeValence_2
    Node -> Tester_49
Tester_49
    BOOL_OP = OR
    COMPOSITE_TEST = 1
    TEST_CLAUSE = TEST @Value(valence) = 3
    TEST_MODE = TEST
    PASSED -> AttributeCreator_15
Tester_44
    BOOL_OP = OR
    COMPOSITE_TEST = 1
    TEST_CLAUSE = TEST @Value(igds_level_name) = REF_3001_RD_Axis_Paved_GRD_Ln
    TEST_MODE = TEST
    PASSED -> NodeValence_3 [Line]
    FAILED -> Tester_45
NodeValence_3
    Node -> Tester_51
Tester_51
    BOOL_OP = OR
    COMPOSITE_TEST = 1
    TEST_CLAUSE = TEST @Value(valence) = 3
    TEST_MODE = TEST
    PASSED -> AttributeCreator_15
Tester_45
    BOOL_OP = OR
    COMPOSITE_TEST = 1
    TEST_CLAUSE = TEST @Value(igds_level_name) = REF_1003_Axis_SING_Carriageway_GRD_Use_ENL_Ln
    TEST_MODE = TEST
    PASSED -> NodeValence_4 [Line]
    FAILED -> Tester_46
NodeValence_4
    Node -> Tester_52
Tester_52
    BOOL_OP = OR
    COMPOSITE_TEST = 1
    TEST_CLAUSE = TEST @Value(valence) = 3
    TEST_MODE = TEST
    PASSED -> AttributeCreator_15
Tester_46
    BOOL_OP = OR
    COMPOSITE_TEST = 1
    TEST_CLAUSE = TEST @Value(igds_level_name) = REF_1003_Axis_SING_Carriageway_GRD_Use_Trunk_Ln
    TEST_MODE = TEST
    PASSED -> NodeValence_5 [Line]
    FAILED -> Tester_47
NodeValence_5
    Node -> Tester_53
Tester_53
    BOOL_OP = OR
    COMPOSITE_TEST = 1
    TEST_CLAUSE = TEST @Value(valence) = 3
    TEST_MODE = TEST
    PASSED -> AttributeCreator_15
Tester_47
    BOOL_OP = OR
    COMPOSITE_TEST = 1
    TEST_CLAUSE = TEST @Value(igds_level_name) = REF_1002_Dual_Carriageway_RD_DOBL_Axis_GRD_Use_Trunk_Ln
    TEST_MODE = TEST
    PASSED -> NodeValence_6 [Line]
    FAILED -> Tester_48
NodeValence_6
    Node -> Tester_54
Tester_54
    BOOL_OP = OR
    COMPOSITE_TEST = 1
    TEST_CLAUSE = TEST @Value(valence) = 3
    TEST_MODE = TEST
    PASSED -> AttributeCreator_15
Tester_48
    BOOL_OP = OR
    COMPOSITE_TEST = 1
    TEST_CLAUSE = TEST @Value(igds_level_name) = REF_1002_Dual_Carriageway_RD_DOBL_Axis_GRD_Use_ENL_Ln
    TEST_MODE = TEST
    PASSED -> NodeValence_7 [Line]
NodeValence_7
    Node -> Tester_55
Tester_55
    BOOL_OP = OR
    COMPOSITE_TEST = 1
    TEST_CLAUSE = TEST @Value(valence) = 3
    TEST_MODE = TEST
    PASSED -> AttributeCreator_15
AttributeCreator_15
    ATTR_TABLE = SET_TO igds_level_name = Err_CNX_Outside-RD_POLY_@Value(valence)
    -> Junction_5
Tester_58
    BOOL_OP = OR
    COMPOSITE_TEST = 1
    TEST_CLAUSE = TEST @Value(Test_Name) = TRACK_CNX_TEST
    TEST_MODE = TEST
    PASSED -> StatisticsCalculator
StatisticsCalculator
    CALCULATION_MODE = NUMERIC
    FEAT_STATS = igds_level_name,NUMERIC_MODE,,,COUNT,,,,,,,,,
    GROUP_BY = igds_level_name
Tester_59
    BOOL_OP = OR
    COMPOSITE_TEST = 1
    TEST_CLAUSE = TEST @Value(igds_level_name) = REF_3002_Trackpath_GRD_Ln
    TEST_MODE = TEST
    PASSED -> Snipper_2
Snipper_2
    DEAGGREGATE_INPUT = YES
    ENDLOCATIONATTR = 99.5
    MEASUREMENTTYPE = 2D
    SNIPMODE = Distance (Percentage)
    STARTLOCATIONATTR = 0.5
    -> SpatialFilter_6 [Candidate]
Tester_56
    BOOL_OP = OR
    COMPOSITE_TEST = 1
    TEST_CLAUSE = TEST @Value(Axis/EDGE/Poly) = Poly
    TEST_MODE = TEST
    PASSED -> SpatialFilter_6 [Filter]
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> AttributeCreator_21
AttributeCreator_21
    ATTR_TABLE = SET_TO igds_level_name = Err_CNX_Track_Inside_POLY@Value(Sub-group_Test)
    -> Junction_5
Junction_5
    -> 05007_Sports_Footbal_Shp (writer DGNV8_2)

Bookmark: WATER_FINAL_01_CNX
Note: WATER_FINAL_01_CNX
Tester_77
    BOOL_OP = OR
    COMPOSITE_TEST = 1
    TEST_CLAUSE = TEST @Value(Test_Name) = HYDRO_POLY_CNX_CHECK
    TEST_MODE = TEST
    PASSED -> Tester_80
Tester_80
    BOOL_OP = OR
    COMPOSITE_TEST = 1
    TEST_CLAUSE = TEST @Value(Axis/EDGE/Poly) = Poly-Round
    TEST_MODE = TEST
    PASSED -> SpatialFilter_15 [Filter]
    PASSED -> Intersector_9
    FAILED -> Tester_81
Tester_81
    BOOL_OP = OR
    COMPOSITE_TEST = 1
    TEST_CLAUSE = TEST @Value(Axis/EDGE/Poly) = HYDRO-CNX
    TEST_MODE = TEST
    PASSED -> SpatialFilter_15 [Candidate]
    FAILED -> Tester_82
SpatialFilter_15
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> LineCombiner_20
LineCombiner_20
    ACCUM_ATTRS_NAME = Use Attributes From One Feature
    BREAK = no
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    PRESERVE = no
    TOPOLOGY = End noded
    LINE -> CoordinateExtractor_2
    LINE -> CoordinateExtractor_3
CoordinateExtractor_2
    IND = 0
    MODE = Specify Coordinate
    X_ATTR = _x
    Y_ATTR = _y
    Z_ATTR = _z
    -> VertexCreator_2
VertexCreator_2
    MEASURE_TYPE = Continuous
    MODE_NAME = Replace with Point
    XVAL = @Value(_x)
    YVAL = @Value(_y)
    ZVAL = @Value(_z)
    -> PointOnLineOverlayer [POINT]
CoordinateExtractor_3
    IND = -1
    MODE = Specify Coordinate
    X_ATTR = _x
    Y_ATTR = _y
    Z_ATTR = _z
    -> VertexCreator_3
VertexCreator_3
    MEASURE_TYPE = Continuous
    MODE_NAME = Replace with Point
    XVAL = @Value(_x)
    YVAL = @Value(_y)
    ZVAL = @Value(_z)
    -> PointOnLineOverlayer [POINT]
Tester_82
    BOOL_OP = OR
    COMPOSITE_TEST = 1
    TEST_CLAUSE = TEST @Value(Axis/EDGE/Poly) = Poly
    TEST_MODE = TEST
    PASSED -> SpatialFilter_16 [Filter]
    PASSED -> SpatialFilter_14 [Filter]
    PASSED -> Intersector_9
    FAILED -> Tester_83
Tester_83
    BOOL_OP = OR
    COMPOSITE_TEST = 1
    TEST_CLAUSE = TEST @Value(Axis/EDGE/Poly) = HYDRO-AXIS
    TEST_MODE = TEST
    PASSED -> LineCombiner_19
    PASSED -> PointOnLineOverlayer_2 [LINE]
    FAILED -> PointOnLineOverlayer [LINE]
    FAILED -> LineCombiner_21
LineCombiner_19
    ACCUM_ATTRS_NAME = Use Attributes From One Feature
    BREAK = no
    CONNECT_Z_MODE = First Wins
    CONSIDER_NODE_ELEVATION = no
    DEAGGREGATE_GEOMETRY = Deaggregate
    DIRECTION_NAME = _direction
    JUNCTIONS_IGNORE_ATTRIBUTES = No
    LINES_AS_SEGMENTS = No
    PRESERVE = no
    TOPOLOGY = End noded
    LINE -> SpatialFilter_16 [Candidate]
SpatialFilter_16
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> AttributeCreator_24
PointOnLineOverlayer
    DEAGGREGATE_INPUT = Yes
    MEASURE_TYPE = Continuous
    MERGE_MEASURES = Yes
    OV_ATTR = _overlaps
    TOLERANCE = 0.1
    POINT -> Tester_84
Tester_84
    BOOL_OP = OR
    COMPOSITE_TEST = 1
    TEST_CLAUSE = TEST @Value(_overlaps) = 0
    TEST_MODE = TEST
    PASSED -> PointOnLineOverlayer_2 [POINT]
PointOnLineOverlayer_2
    DEAGGREGATE_INPUT = Yes
    MEASURE_TYPE = Continuous
    MERGE_MEASURES = Yes
    OV_ATTR = _overlaps
    TOLERANCE = 0.1
    POINT -> Tester_85
Tester_85
    BOOL_OP = OR
    COMPOSITE_TEST = 1
    TEST_CLAUSE = TEST @Value(_overlaps) = 0
    TEST_MODE = TEST
    PASSED -> AttributeCreator_25
AttributeCreator_25
    ATTR_TABLE = SET_TO igds_level_name = Err_Hydro_CNX_@Value(Sub-group_Test)
    -> Junction_8
LineCombiner_21
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Snipper_7
Snipper_7
    DEAGGREGATE_INPUT = YES
    ENDLOCATIONATTR = 99.5
    MEASUREMENTTYPE = 2D
    SNIPMODE = Distance (Percentage)
    STARTLOCATIONATTR = 0.5
    -> Intersector_9
Intersector_9
    ATTRS_ACCUM_MODE = Use Attributes From One Feature
    CLEANING_TOLERANCE = 0.1
    DEAGGREGATE_INPUT = Yes
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Tester_75
Tester_75
    BOOL_OP = OR
    COMPOSITE_TEST = 1 OR 2
    TEST_CLAUSE:
      TEST @Value(Axis/EDGE/Poly) = Poly
      TEST @Value(Axis/EDGE/Poly) = Poly-Round
    TEST_MODE = TEST
    FAILED -> SpatialFilter_14 [Candidate]
SpatialFilter_14
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS INTERSECTS
    USE_BOUNDING_BOX = No
    PASSED -> AttributeCreator_24
AttributeCreator_24
    ATTR_TABLE = SET_TO igds_level_name = Err_No_Hydro_POLYGON_Lines_@Value(Sub-group_Test)
    -> Junction_8
Junction_8
    -> 05007_Sports_Footbal_Shp (writer DGNV8_2)

Bookmark: CNX-HYDRo
Note: CNX-HYDRo
Tester_16 [off]
    BOOL_OP = OR
    COMPOSITE_TEST = 1
    TEST_CLAUSE = TEST @Value(Test_Name) = HYDRO_POLY_CNX_CHECK
    TEST_MODE = TEST
    PASSED -> Tester_17 [off]
Tester_17 [off]
    BOOL_OP = OR
    COMPOSITE_TEST = 1
    TEST_CLAUSE = TEST @Value(Sub-group_Test) = HYDRO-POLY-SHP
    TEST_MODE = TEST
    PASSED -> GeometryFilter_4 [off]
    PASSED -> Tester_60 [off]
    FAILED -> Tester_18 [off]
GeometryFilter_4 [off]
    BREAK_AGG = No
    GEOM_PORT_NAMES = Area
    <UNFILTERED> -> AttributeCreator_6 [off]
    AREA -> Intersector_5 [off]
    AREA -> SpatialFilter_12 [Filter] [off]
Tester_18 [off]
    BOOL_OP = OR
    COMPOSITE_TEST = 1
    TEST_CLAUSE = TEST @Value(Axis/EDGE/Poly) = HYDRO-AXIS
    TEST_MODE = TEST
    PASSED -> LineCombiner_11 [off]
    FAILED -> Tester_61 [off]
LineCombiner_11 [off]
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Intersector_5 [off]
    <REJECTED> -> AttributeCreator_6 [off]
Intersector_5 [off]
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Tester_20 [off]
Tester_20 [off]
    BOOL_OP = OR
    COMPOSITE_TEST = 1
    TEST_CLAUSE = TEST @Value(Axis/EDGE/Poly) = Poly
    TEST_MODE = TEST
    FAILED -> Snipper_5 [off]
Snipper_5 [off]
    DEAGGREGATE_INPUT = YES
    ENDLOCATIONATTR = 99.5
    MEASUREMENTTYPE = 2D
    SNIPMODE = Distance (Percentage)
    STARTLOCATIONATTR = 0.5
    -> SpatialFilter_12 [Candidate] [off]
SpatialFilter_12 [off]
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_8 [off]
AttributeCreator_8 [off]
    ATTR_TABLE = SET_TO igds_level_name = Err_HYDRO_AXIS_In_POLY_@Value(Sub-group_Test)
    -> Junction_6 [off]
Tester_61 [off]
    BOOL_OP = OR
    COMPOSITE_TEST = 1
    TEST_CLAUSE = TEST @Value(Axis/EDGE/Poly) = HYDRO-CNX
    TEST_MODE = TEST
    PASSED -> LineCombiner_12 [off]
    FAILED -> Tester_66 [off]
LineCombiner_12 [off]
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Intersector_7 [off]
    <REJECTED> -> AttributeCreator_6 [off]
Tester_66 [off]
    BOOL_OP = OR
    COMPOSITE_TEST = 1
    TEST_CLAUSE = TEST @Value(Axis/EDGE/Poly) = HYDRO-LINEAR-AXIS
    TEST_MODE = TEST
    PASSED -> LineCombiner_13 [off]
LineCombiner_13 [off]
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> LineOnAreaOverlayer_5 [LINE] [off]
    LINE -> LineOnLineOverlayer [LINE] [off]
Tester_60 [off]
    BOOL_OP = OR
    COMPOSITE_TEST = 1
    TEST_CLAUSE = TEST @Value(Axis/EDGE/Poly) = Poly
    TEST_MODE = TEST
    PASSED -> GeometryFilter_5 [off]
GeometryFilter_5 [off]
    BREAK_AGG = No
    GEOM_PORT_NAMES = Area
    AREA -> Intersector_7 [off]
    AREA -> SpatialFilter_13 [Filter] [off]
    <UNFILTERED> -> AttributeCreator_6 [off]
AttributeCreator_6 [off]
    ATTR_TABLE = SET_TO igds_level_name = Err_HYDRO_CNX_Wrong_Geometry_@Value(Sub-group_Test)
    -> Junction_6 [off]
Intersector_7 [off]
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Tester_62 [off]
Tester_62 [off]
    BOOL_OP = OR
    COMPOSITE_TEST = 1
    TEST_CLAUSE = TEST @Value(Axis/EDGE/Poly) = Poly
    TEST_MODE = TEST
    FAILED -> Counter_2 [off]
Counter_2 [off]
    CNT_ATTR = HYD_ID
    DOMAIN = counter
    SCOPE = Global
    START = 1
    -> Snipper_6 [off]
    -> FeatureJoiner_2 [LEFT] [off]
Snipper_6 [off]
    DEAGGREGATE_INPUT = YES
    ENDLOCATIONATTR = 99.5
    MEASUREMENTTYPE = 2D
    SNIPMODE = Distance (Percentage)
    STARTLOCATIONATTR = 0.5
    -> SpatialFilter_13 [Candidate] [off]
SpatialFilter_13 [off]
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> FeatureJoiner_2 [RIGHT] [off]
FeatureJoiner_2 [off]
    ATTR_CONFLICT_RES = Use Left
    GEOMETRY_HANDLING = Use Left
    JOIN_KEYS = HYD_ID HYD_ID AUTO
    JOIN_MODE = Inner
    JOINED -> LineCombiner_14 [off]
LineCombiner_14 [off]
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Bufferer [off]
    LINE -> LineOnLineOverlayer [LINE] [off]
LineOnLineOverlayer [off]
    ATTRS_ACCUM_MODE = Use Attributes From One Feature
    CLEANING_TOLERANCE = 0.1
    DEAGGREGATE_INPUT = Yes
    GENERATE_LIST_DROP = YES
    LIST_NAME = 1_
    OV_ATTR = _overlaps_1
    SEPARATE_COLLINEAR_SEGMENTS = No
Bufferer [off]
    ANGLE = 22.5
    CAP_STYLE = Arc
    CORNER_STYLE = Arc
    MODE = AREA
    OFFSET = 0.01
    OFFSET_UNITS = NONE
    PRECISION = APPROX
    BUFFERED -> LineOnAreaOverlayer_5 [AREA] [off]
LineOnAreaOverlayer_5 [off]
    ATTR_ACCUM_MODE = Prefix Incoming
    CLEANING_TOLERANCE = 0.1
    DEAGGREGATE_INPUT = Yes
    INCOMING_PREFIX = _E_
    OV_ATTR = _overlaps
    AREA -> Tester_65 [off]
Tester_65 [off]
    BOOL_OP = OR
    COMPOSITE_TEST = 1
    TEST_CLAUSE = TEST @Value(_overlaps) = 2
    TEST_MODE = TEST
    FAILED -> AttributeCreator_23 [off]
AttributeCreator_23 [off]
    ATTR_TABLE = SET_TO igds_level_name = Err_HYDRO_CNX_@Value(_overlaps)_@Value(Sub-group_Test)
    -> Junction_6 [off]
Junction_6 [off]
    -> 05007_Sports_Footbal_Shp (writer DGNV8_2)

Bookmark: VAD_CHECK-CROSSINGS
Note: VAD_CHECK-CROSSINGS
Tester_67
    BOOL_OP = OR
    COMPOSITE_TEST = 1
    TEST_CLAUSE = TEST @Value(Test_Name) = VAD_DOUBT-01
    TEST_MODE = TEST
    PASSED -> Tester_68
    PASSED -> StatisticsCalculator_2
Tester_68
    BOOL_OP = OR
    COMPOSITE_TEST = 1
    TEST_CLAUSE = TEST @Value(Sub-group_Test) = VAD_Hydro_CHK
    TEST_MODE = TEST
    PASSED -> Counter_3
    FAILED -> Counter_4
Counter_3
    CNT_ATTR = _VAD_HYDRO_INT_ID
    DOMAIN = counter
    SCOPE = Global
    START = 1
    -> LineCombiner_15
LineCombiner_15
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Intersector_8
    LINE -> NodeValence_8 [Line]
NodeValence_8
    Node -> Tester_72
Tester_72
    BOOL_OP = OR
    COMPOSITE_TEST = 1 OR 2
    TEST_CLAUSE:
      TEST @Value(valence) = 1
      TEST @Value(valence) = 2
    TEST_MODE = TEST
    FAILED -> PointOnPointOverlayer [POINT]
Counter_4
    CNT_ATTR = _VAD_RD_INT_ID
    DOMAIN = counter
    SCOPE = Global
    START = 1
    -> LineCombiner_16
LineCombiner_16
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Intersector_8
    LINE -> NodeValence_9 [Line]
Intersector_8
    ATTRS_ACCUM_MODE = Merge Attributes
    CLEANING_TOLERANCE = 0.01
    DEAGGREGATE_INPUT = Yes
    DIRECTION_NAME = _direction
    DUPLICATE_Z_NODES = No
    GENERATE_LIST_DROP = YES
    INCOMING_PREFIX = _IN_
    LIST_ATTRS_TO_INCLUDE = igds_level_name _count Axis/EDGE/Poly Sub-group_Test Test_Name
    LIST_NAME = _INT_
    MEASURE_TYPE = Continuous
    NODE_NUM_ATTR = _node_number
    OV_ATTR = _overlaps
    SEG_ATTR = _segments
    SEPARATE_COLLINEAR_SEGMENTS = No
    INTERSECTED -> NodeValence [Line]
NodeValence
    Node -> Tester_69
Tester_69
    BOOL_OP = OR
    COMPOSITE_TEST = 1 OR 2
    TEST_CLAUSE:
      TEST @Value(valence) = 1
      TEST @Value(valence) = 2
    TEST_MODE = TEST
    FAILED -> Tester_71
Tester_71
    BOOL_OP = OR
    COMPOSITE_TEST = 1 OR 2
    TEST_CLAUSE:
      TEST @Value(valence) = 0
      TEST @Value(valence) = 1
    TEST_MODE = TEST
    FAILED -> PointOnPointOverlayer [POINT]
PointOnPointOverlayer
    DEAGGREGATE_INPUT = Yes
    OV_ATTR = _overlaps
    TOLERANCE = 0.1
    POINT -> Tester_78
Tester_78
    BOOL_OP = OR
    COMPOSITE_TEST = 1
    TEST_CLAUSE = TEST @Value(_overlaps) = 0
    TEST_MODE = TEST
    PASSED -> PointOnPointOverlayer_2 [POINT]
NodeValence_9
    Node -> Tester_74
Tester_74
    BOOL_OP = OR
    COMPOSITE_TEST = 1 OR 2
    TEST_CLAUSE:
      TEST @Value(valence) = 1
      TEST @Value(valence) = 2
    TEST_MODE = TEST
    FAILED -> PointOnPointOverlayer_2 [POINT]
PointOnPointOverlayer_2
    DEAGGREGATE_INPUT = Yes
    OV_ATTR = _overlaps
    TOLERANCE = 0.1
    POINT -> Tester_79
Tester_79
    BOOL_OP = OR
    COMPOSITE_TEST = 1
    TEST_CLAUSE = TEST @Value(_overlaps) = 0
    TEST_MODE = TEST
    PASSED -> AttributeCreator
AttributeCreator
    ATTR_TABLE = SET_TO igds_level_name = Err_CHK_HYDRO_ROAD_SNAP_CNX_VAD_Possibility
    -> Junction_7
Junction_7
    -> 05007_Sports_Footbal_Shp (writer DGNV8_2)
StatisticsCalculator_2
    CALCULATION_MODE = NUMERIC
    FEAT_STATS = igds_level_name,NUMERIC_MODE,,,COUNT,,,,,,,,,
    GROUP_BY = igds_level_name

FME custom transformer NodeValence
Notes
    This transformer builds arc-node topology in attributes to mimic
    ARC/INFO
    Coverage network topology and adds 
    valence
    . See 
        topology_basics
    for some good diagrams and further discussion. After editing or filtering this process needs to be rerun, just like an
    ARC/INFO Build
    command to rebuild the correct relationships with new feature counts. The original system keys all ended in "#". The topology stack was stored as a series of layers inside a single dataset called a
    coverage
    .
    The lines have topology attributes exposed in the
    AAT
    table and nodes have attributes in the 
    NAT
    table, hence the suffix names 
    _aat
    and 
    _nat
    . The two featuretypes (lines and points) are intended to be considered as a single set. Not included in the
    AAT
    table is polygon topology which would contain the LPOLY# and RPOLY# identifiers.
    This process includes the equivalent of
    CLEAN
    which breaks all arcs at junctions, explodes all multiparts, removes all coincident lines and vertices.
    The addition of a 
    valence
    to the 
    NAT
    table is useful for analysis to classify
    dangles
    (1),
    pseudonodes
    (2),
    tees
    (3),
    intersections
    (4) or
    multiple junctions 
    (>4)
    .
    The arcs (lines) contain a foreign key to the 
    node_id
    in the 
    fnode
    and 
    tnode
    attributes to allow arcs to be tested for 
    direction 
    relative to the nodes.
    * Indexing the keys will be essential for reasonable performance when selecting or joining these two tables. Indexing in 
    ARC/INFO
    is implied because the original keys with a "#" in the name are the record number similiar to OBJECTID.
    * Tolerance defaults to 0.1 metre
    * The 
    arc_id
    is just one of the arcs joining the node as in the original model.
    * If arcs are not already split they will be split and therefore will duplicate existing attributes.
    * The fme_feature_ type is used to name the outputs the same as the source featuretype with a suffix _aat and _nat
Input is a branched polyline network <ft>
    Output is a cleaned line featuretype <ft>_aat and point representing nodes <ft>_nat
lines (PK arc_id) have fnode_id and tnode_id
nodes have node_id and valence and arc_id as first connecting arc
    Valence is a count of the number of arcs connecting at a node.

Note: Notes / This transformer builds arc-node topology in attributes to mimic ARC/INFO Coverage network topology and adds valence. See topology_basics for some good diagrams and further discussion. After editing or filtering this process needs to be rerun, just like an ARC/INFO Build command to rebuild the correct relationships with new feature counts. The original system keys all ended in "#". The topology stack was stored as a series of layers inside a single dataset called a coverage. / The lines have topology attributes exposed in the AAT table and nodes have attributes in the NAT table, hence the suffix names _aat and _nat. The two featuretypes (lines and points) are intended to be considered as a single set. Not included in the AAT table is polygon topology which would contain the LPOLY# and RPOLY# identifiers. / This process includes the equivalent of CLEAN which breaks all arcs at junctions, explodes all multiparts, removes all coincident lines and vertices. / The addition of a valence to the NAT table is useful for analysis to classify dangles (1), pseudonodes (2), tees (3), intersections (4) or multiple junctions (>4). / The arcs (lines) contain a foreign key to the node_id in the fnode and tnode attributes to allow arcs to be tested for direction relative to the nodes. / * Indexing the keys will be essential for reasonable performance when selecting or joining these two tables. Indexing in ARC/INFO is implied because the original keys with a "#" in the name are the record number similiar to OBJECTID. / * Tolerance defaults to 0.1 metre / * The arc_id is just one of the arcs joining the node as in the original model. / * If arcs are not already split they will be split and therefore will duplicate existing attributes. / * The fme_feature_ type is used to name the outputs the same as the source featuretype with a suffix _aat and _nat
Line (input)
    -> AttributeExposer

Bookmark: New Bookmark
Note: Splits arcs if not already split at intersections before assigning unique IDs which is transferred to the node. / Creates a point at every intersection and ends of every arc. Does not duplicate points at common junctions thank goodness / Adds a list of arcs connected to each node for the valence calculator
AttributeExposer
    ATTR_LIST = fme_feature_type
    -> First_Intersector
First_Intersector: Intersector
    DUPLICATE_Z_NODES = No
    LIST_NAME = all_reaches
    OV_ATTR = _overlaps
    PERFORM_SELF_INTERSECTION = No
    SEG_ATTR = _segments
    SEPARATE_COLLINEAR_SEGMENTS = No
    INTERSECTED -> arc_id_counter
arc_id_counter: Counter
    CNT_ATTR = arc_id
    DOMAIN = counter
    SCOPE = Local
    START = 1
    -> Intersector
Intersector
    DUPLICATE_Z_NODES = No
    LIST_NAME = all_reaches
    OV_ATTR = _overlaps
    PERFORM_SELF_INTERSECTION = No
    SEG_ATTR = _segments
    SEPARATE_COLLINEAR_SEGMENTS = No
    INTERSECTED -> Snipper_Begin
    INTERSECTED -> FeatureMerger_2 [REQUESTOR]
    NODE -> Node_id_counter

Bookmark: Distinguish between FNODE and TNODE (NeighborhoodPair does not)
Note: Snipper gets the first and last points. / Geohash is a spatial key to test for spatial coincidence with the nodes
Snipper_Begin
    ENDVERTEXATTR = 0
    SNIPMODE = Vertex
    STARTVERTEXATTR = 0
    -> Geohash_Begin
    REMNANTS -> Snipper_End
Geohash_Begin: GeometryExtractor
    ATTR = from_geohash
    GEOHASH_PRECISION_DISPLAY = ~9.3 mm (12 characters)
    KIND_LONG = Geohash
    OGC_WKT_PRECISION_DISPLAY = Shortened 64-bit
    -> FeatureMerger [REQUESTOR]
Snipper_End
    ENDVERTEXATTR = -1
    SNIPMODE = Vertex
    STARTVERTEXATTR = -1
    -> Geohash_End
Geohash_End: GeometryExtractor
    ATTR = to_geohash
    GEOHASH_PRECISION_DISPLAY = ~9.3 mm (12 characters)
    KIND_LONG = Geohash
    OGC_WKT_PRECISION_DISPLAY = Shortened 64-bit
    -> FeatureMerger_3 [REQUESTOR]
Geohash_node: GeometryExtractor
    ATTR = node_geohash
    GEOHASH_PRECISION_DISPLAY = ~9.3 mm (12 characters)
    KIND_LONG = Geohash
    OGC_WKT_PRECISION_DISPLAY = Shortened 64-bit
    -> FeatureMerger [SUPPLIER]
    -> FeatureMerger_3 [SUPPLIER]

Bookmark: Add node_id and valence
Node_id_counter: Counter
    CNT_ATTR = node_id
    DOMAIN = counter2
    SCOPE = Local
    START = 1
    -> ListElementCounter
Note: Valence
ListElementCounter
    CNT_ATTR = valence
    LIST_NAME = all_reaches{}
    -> AttributeKeeper
    -> Geohash_node
Note: Calculates the valence from the hidden list of arc-ids. / Output the nodes with unique ids. / arc_id is simply one of the connected arcs.
AttributeKeeper
    CREATE_BULK_MODE_FEATURES = No
    KEEP_ATTRS = arc_id,network_id,node_id,valence,fme_feature_type
    -> Node (output)

Bookmark: From Node
FeatureMerger
    ATTR_ACCUM_MODE = Merge Supplier
    ATTR_CONFLICT_RES = Use Requestor
    IGNORE_NULLS = No
    JOIN_KEYS = @Value(from_geohash) @Value(node_geohash) AUTO
    MERGE_TYPE = Attributes Only
    PROCESS_DUPS = No
    SUPPLIERS_FIRST = No
    MERGED -> AttributeCreator
Note: Join back the node_id as the from-node based on a Geohash match
AttributeCreator
    ATTR_LIST = fnode_id,@Value(node_id)
    -> AttributeKeeper_2
AttributeKeeper_2
    CREATE_BULK_MODE_FEATURES = No
    KEEP_ATTRS = arc_id,fnode_id
    -> FeatureMerger_2 [SUPPLIER]
FeatureMerger_2
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> FeatureMerger_4 [REQUESTOR]

Bookmark: To Node
FeatureMerger_3
    ATTR_ACCUM_MODE = Merge Supplier
    ATTR_CONFLICT_RES = Use Requestor
    IGNORE_NULLS = No
    JOIN_KEYS = @Value(to_geohash) @Value(node_geohash) AUTO
    MERGE_TYPE = Attributes Only
    PROCESS_DUPS = No
    SUPPLIERS_FIRST = No
    MERGED -> AttributeCreator_2
Note: Join back the node_id as the to-node based on a Geohash match
AttributeCreator_2
    ATTR_LIST = tnode_id,@Value(node_id)
    -> AttributeKeeper_3
AttributeKeeper_3
    CREATE_BULK_MODE_FEATURES = No
    KEEP_ATTRS = arc_id,tnode_id
    -> FeatureMerger_4 [SUPPLIER]
FeatureMerger_4
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> AttributeRemover

Bookmark: Tidy temp attributes
AttributeRemover
    LIST_ATTRS = all_reaches{} all_reaches{}.arc_id all_reaches{}.direction all_reaches{}.fme_basename all_reaches{}.ID all_reaches{}.name all_reaches{}.network_id all_reaches{}.OBJECTID all_reaches{}.SHAPE_Length
    REMOVE_ATTRS = _overlaps,_segments
    -> Arc (output)
Arc (output)

Bookmark: Write Nodes
Node (output)
