FME workspace shapefile2dgnv8_linear.fmw

Parameters:
- SourceDataset_SHAPEFILE = D:\02_Pilot\Vienna subway\Delivery\vsen delivery\G1_G2_Bahnsteig\SHP\G1_G2_Bahnsteig_linear.shp   # Source Esri Shapefile(s)
- FEATURE_TYPES = G1_G2_Bahnsteig_linear
- DestDataset_DGNV8 = D:\02_Pilot\Vienna subway\Delivery\vsen delivery\UG\New folder\g1g2b.dgn   # Destination Bentley MicroStation Design File

Readers:
- SHAPEFILE_1: SHAPEFILE from $(SourceDataset_SHAPEFILE)

Writers:
- DGNV8_1: DGNV8 to $(DestDataset_DGNV8)

UG_linear (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> TestFilter
TestFilter
    DEFAULT_VALUE = <UNFILTERED>
    PASSED_TEST_GROUP_OUTPUT = FIRST
    TEST_LIST:
      "BOOL_OP,AND,COMPOSITE_TEST,""""""1 AND 2"""""",TEST_CLAUSE,TEST @Value(THEMATIK) = Pipes
      TEST @Value(DIM_H) < 45",@Value(THEMATIK) = Pipes
    @Value(THEMATIK) = Pipes -> AttributeCreator
    <UNFILTERED> -> TestFilter_2
AttributeCreator
    ATTR_TABLE = SET_TO THEMATIK (buffer) = Cable_L
    -> G1_G2_Bahnsteig_linear (writer DGNV8_1)
TestFilter_2
    DEFAULT_VALUE = <UNFILTERED>
    PASSED_TEST_GROUP_OUTPUT = FIRST
    TEST_LIST = "BOOL_OP,OR,COMPOSITE_TEST,""""""1"""""",TEST_CLAUSE,TEST @Value(THEMATIK) = cable",@Value(THEMATIK) = cable
    <UNFILTERED> -> TestFilter_3
    @Value(THEMATIK) = cable -> AttributeCreator_2
AttributeCreator_2
    ATTR_TABLE = SET_TO THEMATIK (buffer) = Cable
    -> G1_G2_Bahnsteig_linear (writer DGNV8_1)
TestFilter_3
    DEFAULT_VALUE = <UNFILTERED>
    PASSED_TEST_GROUP_OUTPUT = FIRST
    TEST_LIST = "BOOL_OP,OR,COMPOSITE_TEST,""""""1"""""",TEST_CLAUSE,TEST @Value(THEMATIK) = CableDUCT",@Value(THEMATIK) = cable
    @Value(THEMATIK) = cable -> AttributeCreator_3
    <UNFILTERED> -> G1_G2_Bahnsteig_linear (writer DGNV8_1)
AttributeCreator_3
    ATTR_TABLE = SET_TO THEMATIK (buffer) = CableDuct
    -> G1_G2_Bahnsteig_linear (writer DGNV8_1)
G1_G2_Bahnsteig_linear (writer DGNV8_1)
    attributes: THEMATIK char(50), RTRTYP integer, ANGLE integer, DETAILS char(20), BETREIBER char(50), MATERIAL char(50), ANZAHL integer, PROFTYP char(50), DIM_L double, DIM_H double, DIM_BEZ char(50), L_QUAL double, HOEHE1 double, H_QUAL1 double, H_BEZ1 char(50), HOEHE2 double, H_QUAL2 double, H_BEZ2 char(50)
