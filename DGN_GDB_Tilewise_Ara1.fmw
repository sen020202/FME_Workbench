FME workspace DGN_GDB_Tilewise_Ara1.fmw

Parameters:
- SourceDataset_DGNV8 = C:\JEGO\Sunshine\Client-Correction\Final\521\Production\GDB-03\521-Prod.dgn   # Source Bentley MicroStation Design File(s)
- FEATURE_TYPES = 2000_Urban_road_axis_CNX_Unclassified_Generic_Ln 2000_Urban_road_axis_ELE_Generic_Ln 2000_Urban_road_axis_Hidden_Generic_Ln 2000_Urban_road_MNZ_Shp 3001_RD_Axis_Paved_ELE_Ln 3001_RD_Axis_VAD_Paved_Ln 3001_RD_Axis_VAD_UnPaved_Ln 3001_RD_CNX_Paved_Generic_Ln 3001_RD_CNX_UnPaved_Generic_Ln 3001_RD_EDGE_Paved_ELE_Ln 3001_RD_EDGE_VAD_UnPaved_Ln 3001_RD_Linear_UnPaved_ELE_Ln 3001_RD_Linear_VAD_UnPaved_Ln 3001_RD_Paved_ELE_Shp 3001_RD_Paved_GRD_Shp 3001_RD_Paved_VAD_Shp 3001_RD_Unpaved_GRD_Shp 3001_RD_Unpaved_VAD_Shp 3002_Trackpath_CNX_Ln 3002_Trackpath_VAD_Ln 04001_Urban_Nucleaus_BLOCKS_MNZ_Use_Shp 04005_Building_Courtyard_Use_Shp 04007_Sing_Build_SL_Health_Center_Use_Shp 04007_Sing_Build_SL_Use_Church_Pnt 04007_Sing_Build_SL_Use_CityHall_Pnt 04008_Element_Construct_Block_MNZ_Line_Use_Ln 04010_Urban_Nucleaus_Polygon_Shp 05001_Camping_Use_Shp 05007_Sports_Footbal_Shp 05007_Sports_Other_Shp 05007_Sports_Tennis_Shp 06002_ARTIFI_IRRI_Ditch_CNX_Unclassified_Use_Ln 06002_ARTIFI_IRRI_Ditch_LINEAR_Hidden_Use_Ln 06004_Non_PER_CNX_Water_Unclassified_Ln 06004_PER_CNX_Water_Unclassified_Ln 06004_PER_WATER_Unclassified_Shp 06007_NON_PER_Lagoon_water_Shp 06007_PER_Lagoon_water_Shp 06007_Pond_Pool_Water_Shp 06007_Pond_WATER_Reservoir_Veg_Shp 06007_Pond_WATER_Reservoir_Water_Shp 06007_Swim_Pool_Shp 07005_CETN_Bridge_Use_Shp 07005_CETN_Parking_Use_Shp 07005_Ditch_roadside_CNX_Unclassified_Ln 08006_Deposit_FCLTY_Water_Surface_Shp 09002_Public_works_Hydro_Earth_DAM_Shp 09002_Public_works_Hydro_Prey_Shp 10001_Trans_Infra_FCLTY_Paved_esplanade_Shp 10001_Trans_Infra_FCLTY_Unpaved_esplanade_Shp 10002_Waste_Accumulation_EDGE_Other_Shp 12000_Separation_Use_0_Ln 12001_Firewall_Shp 12003_Arable_Crop_CUH_Shp 12003_Bare_ground_SUD_Shp 12003_ERI_Shp 12003_Forest_Tree_ARB_Shp 12003_Garden_HUE_Shp 12003_Pasture_PAS_Shp 12003_Rocky_ROQ_Shp 12003_Scrub_MAT_Shp 12003_Woody_Crop_CUL_Shp Crt_Poly_2000_Urban_road_MNZ_Shp Crt_Poly_3001_RD_Paved_GRD_Shp Crt_Poly_3001_RD_Unpaved_GRD_Shp Crt_Poly_04005_Building_Courtyard_Use_Shp Crt_Poly_05002_Mining_FCLTY_Mine_Use_Shp Crt_Poly_05007_Sports_Footbal_Shp Crt_Poly_05007_Sports_Other_Shp Crt_Poly_05007_Sports_Tennis_Shp Crt_Poly_06004_PER_WATER_Unclassified_Shp Crt_Poly_06007_NON_PER_Lagoon_water_Shp Crt_Poly_06007_PER_Lagoon_water_Shp Crt_Poly_06007_Pond_Pool_Water_Shp Crt_Poly_06007_Pond_WATER_Reservoir_Veg_Shp Crt_Poly_06007_Pond_WATER_Reservoir_Water_Shp Crt_Poly_06007_Swim_Pool_Shp Crt_Poly_07005_CETN_Parking_Use_Shp Crt_Poly_08006_Deposit_FCLTY_Water_Surface_Shp Crt_Poly_09002_Public_works_Hydro_Earth_DAM_Shp Crt_Poly_09002_Public_works_Hydro_Prey_Shp Crt_Poly_10001_Trans_Infra_FCLTY_Paved_esplanade_Shp Crt_Poly_10001_Trans_Infra_FCLTY_Unpaved_esplanade_Shp Crt_Poly_10002_Waste_Accumulation_EDGE_Other_Shp Crt_Poly_12001_Firewall_Shp Crt_Poly_12003_Arable_Crop_CUH_Shp Crt_Poly_12003_Bare_ground_SUD_Shp Crt_Poly_12003_ERI_Shp Crt_Poly_12003_Forest_Tree_ARB_Shp Crt_Poly_12003_Garden_HUE_Shp Crt_Poly_12003_Pasture_PAS_Shp Crt_Poly_12003_Rocky_ROQ_Shp Crt_Poly_12003_Scrub_MAT_Shp Crt_Poly_12003_Woody_Crop_CUL_Shp Crt_Poly_REF_12003_Arable_Crop_CUH_TXT Crt_Poly_REF_12003_Bare_ground_SUD_TXT Crt_Poly_REF_12003_Forest_Tree_ARB_TXT Crt_Poly_REF_12003_Meadow_PRD_TXT Crt_Poly_REF_12003_Pasture_PAS_TXT Crt_Poly_REF_12003_Scrub_MAT_TXT Crt_Poly_REF_12003_Woody_Crop_CUL_TXT FME_Created_PNT_04005_Building_Building_ABN_Shp FME_Created_PNT_04005_Building_Building_Use_Shp FME_Created_PNT_04005_Building_Courtyard_Use_Shp FME_Created_PNT_04005_Building_Greenhouse_Use_Shp FME_Created_PNT_04005_Building_Industrial_Building_Use_Shp FME_Created_PNT_04005_Building_Light_building_Shed_Use_Shp FME_Created_PNT_04005_Building_Marquee_Use_Shp FME_Created_Poly_04005_Building_Building_ABN_Shp FME_Created_Poly_04005_Building_Building_Use_Shp FME_Created_Poly_04005_Building_Courtyard_Use_Shp FME_Created_Poly_04005_Building_Greenhouse_Use_Shp FME_Created_Poly_04005_Building_Industrial_Building_Use_Shp FME_Created_Poly_04005_Building_Light_building_Shed_Use_Shp FME_Created_Poly_04005_Building_Marquee_Use_Shp REF_2000_Urban_road_axis_GRD_Generic_Ln REF_3001_RD_Axis_Paved_GRD_Ln REF_3001_RD_Axis_UnPaved_GRD_Ln REF_3001_RD_EDGE_Paved_GRD_Ln REF_3001_RD_EDGE_UnPaved_GRD_Ln REF_3001_RD_Linear_Paved_GRD_Ln REF_3001_RD_Linear_UnPaved_GRD_Ln REF_03002_Depression_Contour_Ln REF_03002_Master_Contour_Ln REF_03002_Normal_Contour_Ln REF_3002_Trackpath_GRD_Ln REF_03003_Elev_Elevated_Construction_Pnt REF_03003_Elev_Hill_Top_Pnt REF_03003_Elev_Terrain_Generic_Pnt REF_03003_Elev_Terrain_Top_Pnt REF_03003_Sleep_Foot_Ln REF_03003_Sleep_Head_Ln REF_03003_Slope_foot_embankment_Ln REF_03003_Slope_Head_cutting_Ln REF_03003_Slope_head_embankment_Ln REF_03003_Terrace_Margin_Ln REF_04003_Retaining_wall_Ln REF_04003_Wall_Ln REF_04003_Wire_fence_Ln REF_04005_Building_EDGE_Building_ABN_Ln REF_04005_Building_EDGE_Building_Use_Ln REF_04005_Building_EDGE_Courtyard_Use_Ln REF_04005_Building_EDGE_Greenhouse_Use_Ln REF_04005_Building_EDGE_Industrial_Building_Use_Ln REF_04005_Building_EDGE_Light_building_Shed_Use_Ln REF_04005_Building_EDGE_Marquee_Use_Ln REF_04008_Element_Construct_Curb_Use_Ln REF_05002_Mining_FCLTY_Mine_EDGE_Use_Ln REF_05007_Sports_EDGE_Footbal_Ln REF_05007_Sports_EDGE_Other_Ln REF_05007_Sports_EDGE_Paintlines-Field_Ln REF_06002_ARTIFI_IRRI_Ditch_LINEAR_GRD_Use_Ln REF_06004_NATUR_NON_PER_AXIS_Water_Unclassified_Ln REF_06004_NATUR_NON_PER_LINEAR_Water_Unclassified_Ln REF_06004_NATUR_PER_AXIS_Water_Unclassified_Ln REF_06004_NATUR_PER_EDGE_Water_Unclassified_Ln REF_06004_NATUR_PER_LINEAR_Water_Unclassified_Ln REF_06004_PER_EDGE_Water_Unclassified_Ln REF_06006_Coronation_line_Ln REF_06007_EDGE_Swimming_Pool_Ln REF_06007_PER_Lagoon_EDGE_Water_Ln REF_06007_Pond_Pool_EDGE_water_Ln REF_06007_Pond_Water_Reservoir_EDGE_Water_Ln REF_06008_Fountain_Pnt REF_07005_Ditch_roadside_GRD_Ln REF_07005_Schema_Line_Bridge_Use_Ln REF_07005_Tajea_factory_work_Culvert_Ln REF_08003_Enegy_Install_Infra_Laying_Tower_Ln REF_08005_Pipe_Duct_Linear_Surface_Lying_Ln REF_08006_Deposit_FCLTY_EDGE_Water_Surface_Ln REF_09001_Catchment_Well_Pnt REF_09002_Public_works_Hydro_EDGE_Earth_DAM_Tie_Ln REF_09002_Public_works_Hydro_EDGE_Prey_OBR_Ln REF_09002_Public_works_Hydro_Linear_Prey_OBR_Ln REF_10001_Trans_Infra_FCLTY_EDGE_Paved_Esplanade_Ln REF_10001_Trans_Infra_FCLTY_EDGE_Unpaved_Esplanade_Ln REF_12000_Boundary_0_Ln REF_12000_Firewall_Axis_Ln REF_12000_Separation_Use_0_Ln REF_12000L_Firewall_Border_Ln REF_12003_Arable_Crop_CUH_TXT REF_12003_Bare_ground_SUD_TXT REF_12003_Forest_Tree_ARB_TXT REF_12003_Meadow_PRD_TXT REF_12003_Pasture_PAS_TXT REF_12003_Scrub_MAT_TXT REF_12003_Woody_Crop_CUL_TXT Zona_521 "Nivel 49"
- DestDataset_GEODATABASE_FILE = C:\JEGO\Sunshine\Client-Correction\Final\521\Production\GDB-03\521.gdb   # File Geodatabase
- SourceDataset_ESRISHAPE = C:\JEGO\Sunshine\Client-Correction\Final\521\Production\GDB-01\Reference files\**\*.shp   # Source Esri Shapefile(s)
- SourceDataset_XLSXR_3 = $(FME_MF_DIR)Levels_DGN-GDB_12-10-2022-Ver-01.xlsx   # Source Microsoft Excel File(s)
- DestDataset_DGNV8 = C:\JEGO\Sunshine\Client-Correction\Final\521\Production\GDB-03\Err.dgn   # Destination Bentley MicroStation Design File

Readers:
- DGNV8_1: DGNV8 from $(SourceDataset_DGNV8)
- ESRISHAPE_1: ESRISHAPE from $(SourceDataset_ESRISHAPE)
- XLSXR_1: XLSXR from $(SourceDataset_XLSXR_3)

Writers:
- GEODATABASE_FILE_1: GEODATABASE_FILE to $(DestDataset_GEODATABASE_FILE)
- DGNV8_2: DGNV8 to $(DestDataset_DGNV8)

Note: Reference_Files
LimiteAdministrativo_lin (writer GEODATABASE_FILE_1)
    attributes: objectid_2 integer, ID_Fenomen char(5), CODINE1 char(20), CODINE2 char(20), ENCLAVE1 char(20), ENCLAVE2 char(20), ID_LINLIM char(43), MUN1 char(250), MUN2 char(250), TIPO char(5), URL_RESOUR char(250), OBJECTID integer
PuntosGeodesicos_pun (writer GEODATABASE_FILE_1)
    attributes: OBJECTID integer, ID_Fenomen char(5), ASTRONOMIC char(8), FECHACALC char(8), GRAVEDAD char(3), H_ORTO float, ID_HOJA char(5), IDCALC char(10), IDENTIFICA char(10), NOMBRE char(254), ORGANISMOC char(250), REDGEODESI char(3), REDNIVELAC char(3), TITULAR char(3)
RedViaria_pun (writer GEODATABASE_FILE_1)
    attributes: objectid integer, ID_Fenomen char(5), EXTENSION char(20), FECHA_ALTA char(8), FUENTE char(40), ID_VIARIA char(20), ID_PORPK char(20), ID_TRAMO char(20), ID_VIAL char(20), NUMERO double, SENTIDO_PK char(3), TIPO_PORPK char(3), ID_HOJA char(5)
Cuadricula_5k_pol (writer GEODATABASE_FILE_1)
    attributes: ID_Fenomen char(5), CF_50K char(5), CF_5K char(5), HUSO char(20), ID_HOJA char(5), NOMBRE char(250)
PuntosGNSS_pun (writer GEODATABASE_FILE_1)
    attributes: OBJECTID integer, ID_Fenomen char(5), COD_IERS char(9), ID_HOJA char(5), IDENTIFICA char(10), RDIS char(250), RED_EPN char(3), RTK char(3), TITULAR char(3)
Relieve_pun_gis (reader XLSXR_1)
    attributes: Dataset_Name char(16), Id number(2,0), SBM_Names char(36), Geometry char(6), Is_Border_Attri char(3), Id00 number(2,0), ID_Fenomen number(6,0), ID_HOJA char(1), CONTEXTO char(4), COTA string, TIPO char(4)
    -> FeatureJoiner_5 [RIGHT]
RedFerro_lin_gis (reader XLSXR_1)
    attributes: Dataset_Name char(17), Id number(3,0), SBM_Names char(50), Geometry char(5), Is_Border_Attri char(3), Id00 number(3,0), ID_Fenomen number(6,0), COMPONEN1D char(4), ANCHO_TIPO char(1), COMPETENCIA char(1), ELECTRIF char(1), ESTADO char(4), ID_HOJA char(1), ID_TRAMO char(1), NOMBRE char(1), NUMVIAS char(4), SITUACION char(4), TITULAR char(1), VELOCIDAD char(1), CODIGOF char(1), ID_TABLERO char(1)
    -> FeatureJoiner_6 [RIGHT]
ServInst_pun_gis (reader XLSXR_1)
    attributes: Dataset_Name char(17), Id number(3,0), SBM_Names char(55), Geometry char(6), Is_Border_Attri char(4), Id00 number(3,0), ID_Fenomen number(6,0), ID_HOJA char(1), NOMBRE number(5,0), TIPO char(4), CODEXPLOT number(5,0), ESTADO char(4), ENERGIA char(4)
    -> FeatureJoiner_11 [RIGHT]
RedViaria_lin_gis (reader XLSXR_1)
    attributes: Dataset_Name char(18), Id number(4,0), SBM_Names char(64), Geometry char(5), Is_Border_Attri char(4), Id00 number(4,0), ID_Fenomen number(6,0), ACCESO number(5,0), ANCHOCS number(5,0), CALZADA number(5,0), CLASE number(5,0), CLASIF char(4), CODIGO number(5,0), DGC_VIA number(5,0), ESTADOFIS number(2,0), FECHA_ALTA char(1), FECHA_BAJA char(1), FIRME number(2,0), FUENTE_V number(5,0), ID_HOJA char(1), ID_TRAMO number(5,0), ID_VIAL number(13,0), ITINERANCIA number(5,0), LOCALIDAD number(5,0), NCARRILES number(5,0), NOMBRE number(5,0), NOMBRE_ALT number(5,0), NOMBRE_CAT number(5,0), ORDEN char(5), ORIGEN_Z number(2,0),
      SENTIDO number(2,0), SITUACION number(2,0), TIPO_TRAMO number(2,0), TIPO_VEHIC char(21), TIPO_VIAL number(5,0), TITULAR number(5,0), VELOCIDAD number(4,0), TIPO char(4), VIA char(4), ESTADO char(4), Id01 number(4,0)
    -> FeatureJoiner_12 [RIGHT]
RedViaria_pol_gis (reader XLSXR_1)
    attributes: Dataset_Name char(18), Id number(3,0), SBM_Names char(57), Geometry char(8), Is_Border_Attri char(3), Id00 number(3,0), ID_Fenomen number(6,0), ID_HOJA char(1), SITUACION number(2,0), ESTADOFIS number(2,0), TITULAR number(5,0), TIPO_TRAMO number(2,0), ORDEN char(5), NOMBRE number(5,0), NOMBRE_ALT number(5,0), ESTADO char(4), TIPO char(4), VIA char(4)
    -> FeatureJoiner_13 [RIGHT]
RedViaria_pun_gis (reader XLSXR_1)
    attributes: Dataset_Name char(18), Id number(2,0), SBM_Names char(39), Geometry char(6), Is_Border_Attri boolean, Id00 number(2,0), ID_Fenomen number(6,0), EXTENSION char(1), FECHA ALTA char(1), FUENTE char(1), ID_VIARIA char(1), ID_PORPK char(1), ID_TRAMO char(1), ID_VIAL char(1), NUMERO string, SENTIDO_PK char(1), TIPO_PORPK char(1), ID_HOJA char(1)
    -> FeatureJoiner_14 [RIGHT]
Common_Sheet (reader XLSXR_1)
    attributes: Dataset_Name char(18), Id number(2,0), SBM_Names char(20), Geometry char(8), Is_Border_Attri boolean, Id00 number(2,0), ID_Fenomen number(5,0), ID_HOJA string, NOMBRE string, TIPO string
    -> FeatureJoiner [RIGHT]
CubiertaTer_lin_gis (reader XLSXR_1)
    attributes: Dataset_Name char(20), Id number(2,0), SBM_Names char(26), Geometry char(5), Is_Border_Attri char(4), Id00 number(2,0), ID_Fenomen number(6,0), ID_HOJA char(1), NOMBRE char(1), TIPO char(1)
    -> FeatureJoiner_2 [RIGHT]
CubiertaTer_pol_gis (reader XLSXR_1)
    attributes: Dataset_Name char(20), Id number(3,0), SBM_Names char(36), Geometry char(8), Is_Border_Attri char(3), Id00 number(3,0), ID_Fenomen number(6,0), ID_HOJA char(1), NOMBRE char(1), TIPO char(4), FIGURA char(4), CODIGO char(1)
    -> FeatureJoiner_3 [RIGHT]
Relieve_lin_gis (reader XLSXR_1)
    attributes: Dataset_Name char(16), Id number(3,0), SBM_Names char(34), Geometry char(5), Is_Border_Attri char(3), Id00 number(3,0), ID_Fenomen number(6,0), ID_HOJA char(1), COMPONEN1D char(4), PROCEDENCIA char(4), CLASIF char(4), SECCION char(4), TIPO char(4), COTA string, ORIGEN number(2,0), SONDA number(2,0)
    -> FeatureJoiner_4 [RIGHT]
RedFerro_pol_gis (reader XLSXR_1)
    attributes: Dataset_Name char(17), Id number(2,0), SBM_Names char(26), Geometry char(8), Is_Border_Attri char(3), Id00 number(2,0), ID_Fenomen number(6,0), ID_HOJA char(1), CODIGOF char(1), ID_TABLERO char(1)
    -> FeatureJoiner_7 [RIGHT]
RedFerro_pun_gis (reader XLSXR_1)
    attributes: Dataset_Name char(17), Id number(2,0), SBM_Names char(28), Geometry char(6), Is_Border_Attri boolean, Id00 number(2,0), ID_Fenomen number(6,0), EXTENSION char(1), FECHA ALTA char(1), FUENTE char(1), ID_FERRO char(1), ID_PORPK char(1), ID_TRAMO char(1), ID_VIAL char(1), NUMERO string, ID_HOJA char(1)
    -> FeatureJoiner_8 [RIGHT]
ServInst_lin_gis (reader XLSXR_1)
    attributes: Dataset_Name char(17), Id number(4,0), SBM_Names char(66), Geometry char(5), Is_Border_Attri char(4), Id00 number(4,0), ID_Fenomen number(6,0), CODEXPLOT char(1), ESTADO char(4), ID_HOJA char(1), NOMBRE number(5,0), TIPO char(4), TITULAR char(4), SITUACION char(4), CLASIF char(4), CORONACION string, COTAMAX string
    -> FeatureJoiner_9 [RIGHT]
ServInst_pol_gis (reader XLSXR_1)
    attributes: Dataset_Name char(17), Id number(4,0), SBM_Names char(60), Geometry char(8), Is_Border_Attri char(4), Id00 number(4,0), ID_Fenomen number(6,0), CODEXPLOT number(5,0), ESTADO char(4), ID_HOJA char(1), NOMBRE number(5,0), TIPO char(4), TITULAR char(4), SITUACION char(4), ENERGIA char(4), CORONACION string, COTAMAX string
    -> FeatureJoiner_10 [RIGHT]
Hidrografia_lin_gis (reader XLSXR_1)
    attributes: Dataset_Name char(20), Id number(3,0), SBM_Names char(51), Geometry char(5), Is_Border_Attri char(4), Id00 number(3,0), ID_Fenomen number(6,0), ESTADO char(4), ID_HOJA char(1), COMPONEN1D char(4), NOMBRE number(5,0), SITUACION char(4), TIPO char(4), CANALIZ char(4), CUENCA char(1), NIVEL_HIDRO char(4), REGIMEN char(4), SUBCUENCA char(1), CLASIF char(4)
    -> FeatureJoiner_15 [RIGHT]
Hidrografia_pol_gis (reader XLSXR_1)
    attributes: Dataset_Name char(20), Id number(3,0), SBM_Names char(41), Geometry char(8), Is_Border_Attri char(3), Id00 number(3,0), ID_Fenomen number(6,0), ESTADO char(4), ID_HOJA char(1), NOMBRE number(5,0), SITUACION char(4), TIPO char(4), CANALIZ char(4), CUENCA char(1), NIVEL_HIDRO char(4), REGIMEN char(4), SUBCUENCA char(1), CLASIF char(4)
    -> FeatureJoiner_16 [RIGHT]
Hidrografia_pun_gis (reader XLSXR_1)
    attributes: Dataset_Name char(20), Id number(2,0), SBM_Names char(29), Geometry char(6), Is_Border_Attri char(3), Id00 number(2,0), ID_Fenomen number(6,0), ID_HOJA char(1), NOMBRE number(5,0), TIPO char(4)
    -> FeatureJoiner_17 [RIGHT]
EdiPobCons_lin_gis (reader XLSXR_1)
    attributes: Dataset_Name char(19), Id number(4,0), SBM_Names char(69), Geometry char(5), Is_Border_Attri char(4), Id00 number(4,0), ID_Fenomen number(6,0), ID_HOJA char(1), TIPO char(4), ESTADO char(4), BIC char(4), CLASIF char(4), SITUACION char(4), USO char(4), NOMBRE number(5,0)
    -> FeatureJoiner_18 [RIGHT]
EdiPobCons_pol_gis (reader XLSXR_1)
    attributes: Dataset_Name char(19), Id number(4,0), SBM_Names char(62), Is_Border_Attri char(3), Geometry char(8), Id00 number(4,0), ID_Fenomen number(6,0), ESTADO char(4), ID_HOJA char(1), TIPO char(4), BIC char(4), CLASIF char(4), NOMBRE number(5,0), SITUACION char(4), USO char(4), C_NUCLEO_I char(1), D_NUCLEO_I char(1)
    -> FeatureJoiner_19 [RIGHT]
EdiPobCons_pun_gis (reader XLSXR_1)
    attributes: Dataset_Name char(19), Id number(4,0), SBM_Names char(60), Geometry char(6), Id00 number(4,0), ID_Fenomen number(6,0), ID_HOJA char(1), NOMBRE number(5,0), TIPO char(4), VISTO char(4), BIC char(4), CLASIF char(4), ESTADO char(4), SITUACION char(4), USO char(4)
    -> FeatureJoiner_20 [RIGHT]
REF_04011_Yard_Garden_Vegetation_Urban_trees_TXT (reader DGNV8_1)
    -> Counter
Counter
    CNT_ATTR = _count
    DOMAIN = counter
    SCOPE = Global
    START = 1
    -> AttributeTrimmer_4
AttributeTrimmer_4
    SRC_ATTRS = igds_level_name
    TRIM_CHARS = REF_
    TRIM_TO_NONE = Yes
    TRIM_TYPE = Left
    -> AttributeTrimmer_3
AttributeTrimmer_3
    SRC_ATTRS = igds_level_name
    TRIM_CHARS = FME_Created_Poly_
    TRIM_TO_NONE = Yes
    TRIM_TYPE = Left
    -> AttributeTrimmer_5
AttributeTrimmer_5
    SRC_ATTRS = igds_level_name
    TRIM_CHARS = Crt_Poly_REF_
    TRIM_TO_NONE = Yes
    TRIM_TYPE = Left
    -> AttributeTrimmer_6
AttributeTrimmer_6
    SRC_ATTRS = igds_level_name
    TRIM_CHARS = FME_Created_PNT_
    TRIM_TO_NONE = Yes
    TRIM_TYPE = Left
    -> AttributeCreator_40
FeatureJoiner
    ATTR_CONFLICT_RES = Use Left
    GEOMETRY_HANDLING = Use Left
    JOIN_KEYS = igds_level_name SBM_Names AUTO
    JOIN_MODE = Inner
    JOINED -> TestFilter
    UNJOINED_LEFT -> FeatureJoiner_2 [LEFT]
TestFilter
    DEFAULT_VALUE = <UNFILTERED>
    TEST_LIST:
      "BOOL_OP,OR,COMPOSITE_TEST,""""""1 OR 2"""""",TEST_CLAUSE,TEST @Value(igds_level_name) = REF_12000_Boundary_0_Ln
      TEST @Value(igds_level_name) = 12000_Boundary_0_Ln",Boundary
FeatureJoiner_2
    ATTR_CONFLICT_RES = Use Left
    GEOMETRY_HANDLING = Use Left
    JOIN_KEYS = igds_level_name SBM_Names AUTO
    JOIN_MODE = Inner
    JOINED -> Tester_3
    UNJOINED_LEFT -> FeatureJoiner_3 [LEFT]
Tester_3
    BOOL_OP = OR
    COMPOSITE_TEST = 1
    TEST_CLAUSE = TEST @Value(Dataset_Name) = CubiertaTer_lin_gis
    TEST_MODE = TEST
    PASSED -> Tester_2
Tester_2
    BOOL_OP = OR
    COMPOSITE_TEST = 1
    TEST_CLAUSE = TEST @Value(Is_Border_Attri) = Yes
    TEST_MODE = TEST
    PASSED -> AttributeCreator_37
    FAILED -> GeometryFilter_2
AttributeCreator_37
    ATTR_TABLE = SET_TO igds_level_name = Chk_BOR_@Value(Dataset_Name)_@Value(igds_level_name)
    -> REF_04011_Yard_Garden_Vegetation_Urban_trees_TXT (writer DGNV8_2)
GeometryFilter_2
    BREAK_AGG = No
    GEOM_PORT_NAMES = Point Line Area Text
    POINT -> AttributeCreator_38
    LINE -> CubiertaTer_lin (writer GEODATABASE_FILE_1)
    AREA -> AttributeCreator_38
    TEXT -> AttributeCreator_38
    <UNFILTERED> -> AttributeCreator_38
CubiertaTer_lin (writer GEODATABASE_FILE_1)
    attributes: ID_Fenomen char(5), ID_HOJA char(5), NOMBRE char(250), TIPO char(5)
AttributeCreator_38
    ATTR_TABLE = SET_TO igds_level_name = Chk_Wrg_Gmetry_@Value(Dataset_Name)_@Value(igds_level_name)
    -> REF_04011_Yard_Garden_Vegetation_Urban_trees_TXT (writer DGNV8_2)
FeatureJoiner_3
    ATTR_CONFLICT_RES = Use Left
    GEOMETRY_HANDLING = Use Left
    JOIN_KEYS = igds_level_name SBM_Names AUTO
    JOIN_MODE = Inner
    JOINED -> Tester_5
    UNJOINED_LEFT -> FeatureJoiner_4 [LEFT]
Tester_5
    BOOL_OP = OR
    COMPOSITE_TEST = 1
    TEST_CLAUSE = TEST @Value(Dataset_Name) = CubiertaTer_pol_gis
    TEST_MODE = TEST
    PASSED -> Tester_4
Tester_4
    BOOL_OP = OR
    COMPOSITE_TEST = 1
    TEST_CLAUSE = TEST @Value(Is_Border_Attri) = Yes
    TEST_MODE = TEST
    PASSED -> AttributeCreator_36
    FAILED -> GeometryFilter
AttributeCreator_36
    ATTR_TABLE = SET_TO igds_level_name = Chk_BOR_@Value(Dataset_Name)_@Value(igds_level_name)
    -> REF_04011_Yard_Garden_Vegetation_Urban_trees_TXT (writer DGNV8_2)
GeometryFilter
    BREAK_AGG = No
    GEOM_PORT_NAMES = Point Line Area Text
    POINT -> AttributeCreator
    LINE -> AttributeCreator
    AREA -> CubiertaTer_pol (writer GEODATABASE_FILE_1)
    TEXT -> AttributeCreator
    <UNFILTERED> -> AttributeCreator
AttributeCreator
    ATTR_TABLE = SET_TO igds_level_name = Chk_Wrg_Gmetry_@Value(Dataset_Name)_@Value(igds_level_name)
    -> REF_04011_Yard_Garden_Vegetation_Urban_trees_TXT (writer DGNV8_2)
CubiertaTer_pol (writer GEODATABASE_FILE_1)
    attributes: ID_Fenomen char(5), ID_HOJA char(5), NOMBRE char(254), TIPO char(5), FIGURA char(5), CODIGO char(9)
FeatureJoiner_4
    ATTR_CONFLICT_RES = Use Left
    GEOMETRY_HANDLING = Use Left
    JOIN_KEYS = igds_level_name SBM_Names AUTO
    JOIN_MODE = Inner
    JOINED -> Tester_7
    UNJOINED_LEFT -> FeatureJoiner_5 [LEFT]
Tester_7
    BOOL_OP = OR
    COMPOSITE_TEST = 1
    TEST_CLAUSE = TEST @Value(Dataset_Name) = Relieve_lin_gis
    TEST_MODE = TEST
    PASSED -> Tester_6
Tester_6
    BOOL_OP = OR
    COMPOSITE_TEST = 1
    TEST_CLAUSE = TEST @Value(Is_Border_Attri) = Yes
    TEST_MODE = TEST
    PASSED -> AttributeCreator_35
    FAILED -> GeometryFilter_3
AttributeCreator_35
    ATTR_TABLE = SET_TO igds_level_name = Chk_BOR_@Value(Dataset_Name)_@Value(igds_level_name)
    -> REF_04011_Yard_Garden_Vegetation_Urban_trees_TXT (writer DGNV8_2)
GeometryFilter_3
    BREAK_AGG = No
    GEOM_PORT_NAMES = Point Line Area Text
    POINT -> AttributeCreator_2
    LINE -> Tester_41
    AREA -> AttributeCreator_2
    TEXT -> AttributeCreator_2
    <UNFILTERED> -> AttributeCreator_2
AttributeCreator_2
    ATTR_TABLE = SET_TO igds_level_name = Chk_Wrg_Gmetry_@Value(Dataset_Name)_@Value(igds_level_name)
    -> REF_04011_Yard_Garden_Vegetation_Urban_trees_TXT (writer DGNV8_2)
Tester_41
    BOOL_OP = OR
    COMPOSITE_TEST = 1 OR 2 OR 3 OR 4
    TEST_CLAUSE:
      TEST @Value(igds_level_name) = 03002_Master_Contour_Ln
      TEST @Value(igds_level_name) = 03002_Auxiliary_Contour_Ln
      TEST @Value(igds_level_name) = 03002_Normal_Contour_Ln
      TEST @Value(igds_level_name) = 03002_Depression_Contour_Ln
    TEST_MODE = TEST
    PASSED -> BoundsExtractor
    FAILED -> Relieve_lin (writer GEODATABASE_FILE_1)
BoundsExtractor
    XMAX = _xmax
    XMIN = _xmin
    YMAX = _ymax
    YMIN = _ymin
    ZMAX = _zmax
    ZMIN = _zmin
    -> AttributeRounder_2
AttributeRounder_2
    PLACES = 3
    ROUND_TYPE = Nearest
    SRC_ATTRS = _zmin
    -> AttributeCreator_41
AttributeCreator_41
    ATTR_TABLE = SET_TO Diff = @sub(@Value(_zmax),@Value(_zmin))
    -> Tester_42
Tester_42
    BOOL_OP = OR
    COMPOSITE_TEST = 1
    TEST_CLAUSE = NUM_TEST @Value(Diff) RANGE [-0.1,0.1]
    TEST_MODE = TEST
    PASSED -> Relieve_lin (writer GEODATABASE_FILE_1)
    FAILED -> AttributeCreator_42
AttributeCreator_42
    ATTR_TABLE = SET_TO igds_level_name = Err_Contour_Height_Mismatch_Correct
    -> REF_04011_Yard_Garden_Vegetation_Urban_trees_TXT (writer DGNV8_2)
Relieve_lin (writer GEODATABASE_FILE_1)
    attributes: SONDA char(20), ID_HOJA char(5), SECCION char(5), TIPO char(5), COTA char(20), COMPONEN1D char(5), ID_Fenomen char(5), CLASIF char(5), ORIGEN char(20), PROCEDENCIA char(5)
FeatureJoiner_5
    ATTR_CONFLICT_RES = Use Left
    GEOMETRY_HANDLING = Use Left
    JOIN_KEYS = igds_level_name SBM_Names AUTO
    JOIN_MODE = Inner
    JOINED -> Tester_9
    UNJOINED_LEFT -> FeatureJoiner_6 [LEFT]
Tester_9
    BOOL_OP = OR
    COMPOSITE_TEST = 1
    TEST_CLAUSE = TEST @Value(Dataset_Name) = Relieve_pun_gis
    TEST_MODE = TEST
    PASSED -> Tester_8
Tester_8
    BOOL_OP = OR
    COMPOSITE_TEST = 1
    TEST_CLAUSE = TEST @Value(Is_Border_Attri) = Yes
    TEST_MODE = TEST
    PASSED -> AttributeCreator_34
    FAILED -> GeometryFilter_4
AttributeCreator_34
    ATTR_TABLE = SET_TO igds_level_name = Chk_BOR_@Value(Dataset_Name)_@Value(igds_level_name)
    -> REF_04011_Yard_Garden_Vegetation_Urban_trees_TXT (writer DGNV8_2)
GeometryFilter_4
    BREAK_AGG = No
    GEOM_PORT_NAMES = Point Line Area Text
    POINT -> CoordinateExtractor
    LINE -> AttributeCreator_3
    AREA -> AttributeCreator_3
    TEXT -> AttributeCreator_3
    <UNFILTERED> -> AttributeCreator_3
AttributeCreator_3
    ATTR_TABLE = SET_TO igds_level_name = Chk_Wrg_Gmetry_@Value(Dataset_Name)_@Value(igds_level_name)
    -> REF_04011_Yard_Garden_Vegetation_Urban_trees_TXT (writer DGNV8_2)
CoordinateExtractor
    IND = 0
    MODE = Specify Coordinate
    X_ATTR = _x
    Y_ATTR = _y
    Z_ATTR = _z
    -> AttributeRounder
AttributeRounder
    PLACES = 3
    ROUND_TYPE = Nearest
    SRC_ATTRS = _z
    -> Relieve_pun (writer GEODATABASE_FILE_1)
Relieve_pun (writer GEODATABASE_FILE_1)
    attributes: ID_Fenomen char(5), ID_HOJA char(5), CONTEXTO char(3), COTA double, TIPO char(3)
FeatureJoiner_6
    ATTR_CONFLICT_RES = Use Left
    GEOMETRY_HANDLING = Use Left
    JOIN_KEYS = igds_level_name SBM_Names AUTO
    JOIN_MODE = Inner
    JOINED -> Tester_11
    UNJOINED_LEFT -> FeatureJoiner_7 [LEFT]
Tester_11
    BOOL_OP = OR
    COMPOSITE_TEST = 1
    TEST_CLAUSE = TEST @Value(Dataset_Name) = RedFerro_lin_gis
    TEST_MODE = TEST
    PASSED -> Tester_10
Tester_10
    BOOL_OP = OR
    COMPOSITE_TEST = 1
    TEST_CLAUSE = TEST @Value(Is_Border_Attri) = Yes
    TEST_MODE = TEST
    PASSED -> AttributeCreator_33
    FAILED -> GeometryFilter_5
AttributeCreator_33
    ATTR_TABLE = SET_TO igds_level_name = Chk_BOR_@Value(Dataset_Name)_@Value(igds_level_name)
    -> REF_04011_Yard_Garden_Vegetation_Urban_trees_TXT (writer DGNV8_2)
GeometryFilter_5
    BREAK_AGG = No
    GEOM_PORT_NAMES = Point Line Area Text
    POINT -> AttributeCreator_4
    LINE -> RedFerro_lin (writer GEODATABASE_FILE_1)
    AREA -> AttributeCreator_4
    TEXT -> AttributeCreator_4
    <UNFILTERED> -> AttributeCreator_4
AttributeCreator_4
    ATTR_TABLE = SET_TO igds_level_name = Chk_Wrg_Gmetry_@Value(Dataset_Name)_@Value(igds_level_name)
    -> REF_04011_Yard_Garden_Vegetation_Urban_trees_TXT (writer DGNV8_2)
RedFerro_lin (writer GEODATABASE_FILE_1)
    attributes: ID_Fenomen char(5), COMPONEN1D char(3), ANCHO_TIPO char(3), COMPETENCIA char(3), ELECTRIF char(3), ESTADO char(3), ID_HOJA char(5), ID_TRAMO char(15), NOMBRE char(250), NUMVIAS char(3), SITUACION char(3), TITULAR char(3), VELOCIDAD char(3), CODIGOF char(15), ID_TABLERO char(15), SHAPE_Length double
FeatureJoiner_7
    ATTR_CONFLICT_RES = Use Left
    GEOMETRY_HANDLING = Use Left
    JOIN_KEYS = igds_level_name SBM_Names AUTO
    JOIN_MODE = Inner
    JOINED -> Tester_13
    UNJOINED_LEFT -> FeatureJoiner_8 [LEFT]
Tester_13
    BOOL_OP = OR
    COMPOSITE_TEST = 1
    TEST_CLAUSE = TEST @Value(Dataset_Name) = RedFerro_pol_gis
    TEST_MODE = TEST
    PASSED -> Tester_12
Tester_12
    BOOL_OP = OR
    COMPOSITE_TEST = 1
    TEST_CLAUSE = TEST @Value(Is_Border_Attri) = Yes
    TEST_MODE = TEST
    PASSED -> AttributeCreator_32
    FAILED -> GeometryFilter_6
AttributeCreator_32
    ATTR_TABLE = SET_TO igds_level_name = Chk_BOR_@Value(Dataset_Name)_@Value(igds_level_name)
    -> REF_04011_Yard_Garden_Vegetation_Urban_trees_TXT (writer DGNV8_2)
GeometryFilter_6
    BREAK_AGG = No
    GEOM_PORT_NAMES = Point Line Area Text
    POINT -> AttributeCreator_5
    LINE -> AttributeCreator_5
    AREA -> RedFerro_pol (writer GEODATABASE_FILE_1)
    TEXT -> AttributeCreator_5
    <UNFILTERED> -> AttributeCreator_5
AttributeCreator_5
    ATTR_TABLE = SET_TO igds_level_name = Chk_Wrg_Gmetry_@Value(Dataset_Name)_@Value(igds_level_name)
    -> REF_04011_Yard_Garden_Vegetation_Urban_trees_TXT (writer DGNV8_2)
RedFerro_pol (writer GEODATABASE_FILE_1)
    attributes: objectid integer, ID_Fenomen char(5), ID_HOJA char(5), CODIGOF char(250), ID_TABLERO char(15), SHAPE_Length double, SHAPE_Area double
FeatureJoiner_8
    ATTR_CONFLICT_RES = Use Left
    GEOMETRY_HANDLING = Use Left
    JOIN_KEYS = igds_level_name SBM_Names AUTO
    JOIN_MODE = Inner
    JOINED -> Tester_15
    UNJOINED_LEFT -> FeatureJoiner_9 [LEFT]
Tester_15
    BOOL_OP = OR
    COMPOSITE_TEST = 1
    TEST_CLAUSE = TEST @Value(Dataset_Name) = RedFerro_pun_gis
    TEST_MODE = TEST
    PASSED -> Tester_14
Tester_14
    BOOL_OP = OR
    COMPOSITE_TEST = 1
    TEST_CLAUSE = TEST @Value(Is_Border_Attri) = Yes
    TEST_MODE = TEST
    PASSED -> AttributeCreator_31
    FAILED -> GeometryFilter_7
AttributeCreator_31
    ATTR_TABLE = SET_TO igds_level_name = Chk_BOR_@Value(Dataset_Name)_@Value(igds_level_name)
    -> REF_04011_Yard_Garden_Vegetation_Urban_trees_TXT (writer DGNV8_2)
GeometryFilter_7
    BREAK_AGG = No
    GEOM_PORT_NAMES = Point Line Area Text
    POINT -> RedFerro_pun (writer GEODATABASE_FILE_1)
    LINE -> AttributeCreator_6
    AREA -> AttributeCreator_6
    TEXT -> AttributeCreator_6
    <UNFILTERED> -> AttributeCreator_6
AttributeCreator_6
    ATTR_TABLE = SET_TO igds_level_name = Chk_Wrg_Gmetry_@Value(Dataset_Name)_@Value(igds_level_name)
    -> REF_04011_Yard_Garden_Vegetation_Urban_trees_TXT (writer DGNV8_2)
RedFerro_pun (writer GEODATABASE_FILE_1)
    attributes: ID_Fenomen char(5), EXTENSION char(20), FECHA_ALTA char(8), FUENTE char(40), ID_FERRO char(20), ID_PORPK char(20), ID_TRAMO char(20), ID_VIAL char(20), NUMERO double, ID_HOJA char(5)
FeatureJoiner_9
    ATTR_CONFLICT_RES = Use Left
    GEOMETRY_HANDLING = Use Left
    JOIN_KEYS = igds_level_name SBM_Names AUTO
    JOIN_MODE = Inner
    JOINED -> Tester_17
    UNJOINED_LEFT -> Tester_40
Tester_17
    BOOL_OP = OR
    COMPOSITE_TEST = 1
    TEST_CLAUSE = TEST @Value(Dataset_Name) = ServInst_lin_gis
    TEST_MODE = TEST
    PASSED -> Tester_16
Tester_16
    BOOL_OP = OR
    COMPOSITE_TEST = 1
    TEST_CLAUSE = TEST @Value(Is_Border_Attri) = Yes
    TEST_MODE = TEST
    PASSED -> AttributeCreator_30
    FAILED -> GeometryFilter_8
AttributeCreator_30
    ATTR_TABLE = SET_TO igds_level_name = Chk_BOR_@Value(Dataset_Name)_@Value(igds_level_name)
    -> REF_04011_Yard_Garden_Vegetation_Urban_trees_TXT (writer DGNV8_2)
GeometryFilter_8
    BREAK_AGG = No
    GEOM_PORT_NAMES = Point Line Area Text
    LINE -> ServInst_lin (writer GEODATABASE_FILE_1)
    AREA -> AttributeCreator_7
    TEXT -> AttributeCreator_7
    <UNFILTERED> -> AttributeCreator_7
AttributeCreator_7
    ATTR_TABLE = SET_TO igds_level_name = Chk_Wrg_Gmetry_@Value(Dataset_Name)_@Value(igds_level_name)
    -> REF_04011_Yard_Garden_Vegetation_Urban_trees_TXT (writer DGNV8_2)
ServInst_lin (writer GEODATABASE_FILE_1)
    attributes: ID_Fenomen char(254), CODEXPLOT char(50), ESTADO char(5), ID_HOJA char(5), NOMBRE char(254), TIPO char(5), TITULAR char(254), SITUACION char(5), CLASIF char(5), CORONACION char(20), COTAMAX char(20)
FeatureJoiner_10
    ATTR_CONFLICT_RES = Use Left
    GEOMETRY_HANDLING = Use Left
    JOIN_KEYS = igds_level_name SBM_Names AUTO
    JOIN_MODE = Inner
    JOINED -> Tester_19
    UNJOINED_LEFT -> FeatureJoiner_11 [LEFT]
Tester_19
    BOOL_OP = OR
    COMPOSITE_TEST = 1
    TEST_CLAUSE = TEST @Value(Dataset_Name) = ServInst_pol_gis
    TEST_MODE = TEST
    PASSED -> Tester_18
Tester_18
    BOOL_OP = OR
    COMPOSITE_TEST = 1
    TEST_CLAUSE = TEST @Value(Is_Border_Attri) = Yes
    TEST_MODE = TEST
    PASSED -> AttributeCreator_29
    FAILED -> GeometryFilter_9
AttributeCreator_29
    ATTR_TABLE = SET_TO igds_level_name = Chk_BOR_@Value(Dataset_Name)_@Value(igds_level_name)
    -> REF_04011_Yard_Garden_Vegetation_Urban_trees_TXT (writer DGNV8_2)
GeometryFilter_9
    BREAK_AGG = No
    GEOM_PORT_NAMES = Point Line Area Text
    POINT -> AttributeCreator_8
    LINE -> AttributeCreator_8
    AREA -> ServInst_pol (writer GEODATABASE_FILE_1)
    TEXT -> AttributeCreator_8
    <UNFILTERED> -> AttributeCreator_8
AttributeCreator_8
    ATTR_TABLE = SET_TO igds_level_name = Chk_Wrg_Gmetry_@Value(Dataset_Name)_@Value(igds_level_name)
    -> REF_04011_Yard_Garden_Vegetation_Urban_trees_TXT (writer DGNV8_2)
ServInst_pol (writer GEODATABASE_FILE_1)
    attributes: ID_Fenomen char(5), CODEXPLOT char(50), ESTADO char(5), ID_HOJA char(5), NOMBRE char(250), TIPO char(5), TITULAR char(5), SITUACION char(5), ENERGIA char(5), CORONACION char(20), COTAMAX char(20)
FeatureJoiner_11
    ATTR_CONFLICT_RES = Use Left
    GEOMETRY_HANDLING = Use Left
    JOIN_KEYS = igds_level_name SBM_Names AUTO
    JOIN_MODE = Inner
    JOINED -> Tester_21
    UNJOINED_LEFT -> FeatureJoiner_12 [LEFT]
Tester_21
    BOOL_OP = OR
    COMPOSITE_TEST = 1
    TEST_CLAUSE = TEST @Value(Dataset_Name) = ServInst_pun_gis
    TEST_MODE = TEST
    PASSED -> Tester_20
Tester_20
    BOOL_OP = OR
    COMPOSITE_TEST = 1
    TEST_CLAUSE = TEST @Value(Is_Border_Attri) = Yes
    TEST_MODE = TEST
    PASSED -> AttributeCreator_28
    FAILED -> GeometryFilter_10
AttributeCreator_28
    ATTR_TABLE = SET_TO igds_level_name = Chk_BOR_@Value(Dataset_Name)_@Value(igds_level_name)
    -> REF_04011_Yard_Garden_Vegetation_Urban_trees_TXT (writer DGNV8_2)
GeometryFilter_10
    BREAK_AGG = No
    GEOM_PORT_NAMES = Point Line Area Text
    POINT -> ServInst_pun (writer GEODATABASE_FILE_1)
    LINE -> AttributeCreator_9
    AREA -> AttributeCreator_9
    TEXT -> AttributeCreator_9
    <UNFILTERED> -> AttributeCreator_9
AttributeCreator_9
    ATTR_TABLE = SET_TO igds_level_name = Chk_Wrg_Gmetry_@Value(Dataset_Name)_@Value(igds_level_name)
    -> REF_04011_Yard_Garden_Vegetation_Urban_trees_TXT (writer DGNV8_2)
ServInst_pun (writer GEODATABASE_FILE_1)
    attributes: objectid integer, ID_Fenomen char(5), ID_HOJA char(5), NOMBRE char(250), TIPO char(3), CODEXPLOT char(50), ESTADO char(3), ENERGIA char(3)
FeatureJoiner_12
    ATTR_CONFLICT_RES = Use Left
    GEOMETRY_HANDLING = Use Left
    JOIN_KEYS = igds_level_name SBM_Names AUTO
    JOIN_MODE = Inner
    JOINED -> Tester_23
    UNJOINED_LEFT -> FeatureJoiner_13 [LEFT]
Tester_23
    BOOL_OP = OR
    COMPOSITE_TEST = 1
    TEST_CLAUSE = TEST @Value(Dataset_Name) = RedViaria_lin_gis
    TEST_MODE = TEST
    PASSED -> Tester_22
Tester_22
    BOOL_OP = OR
    COMPOSITE_TEST = 1 OR 2
    TEST_CLAUSE:
      CASE_INSENSITIVE_TEST @Value(Is_Border_Attri) = Yes
      CASE_INSENSITIVE_TEST @Value(CLASIF) = BOR
    TEST_MODE = CASE_INSENSITIVE_TEST
    PASSED -> AttributeCreator_27
    FAILED -> GeometryFilter_11
AttributeCreator_27
    ATTR_TABLE = SET_TO igds_level_name = Chk_BOR_@Value(Dataset_Name)_@Value(igds_level_name)
    -> REF_04011_Yard_Garden_Vegetation_Urban_trees_TXT (writer DGNV8_2)
GeometryFilter_11
    BREAK_AGG = No
    GEOM_PORT_NAMES = Point Line Area Text
    POINT -> AttributeCreator_10
    LINE -> RedViaria_lin (writer GEODATABASE_FILE_1)
    AREA -> AttributeCreator_10
    TEXT -> AttributeCreator_10
    <UNFILTERED> -> AttributeCreator_10
AttributeCreator_10
    ATTR_TABLE = SET_TO igds_level_name = Chk_Wrg_Gmetry_@Value(Dataset_Name)_@Value(igds_level_name)
    -> REF_04011_Yard_Garden_Vegetation_Urban_trees_TXT (writer DGNV8_2)
RedViaria_lin (writer GEODATABASE_FILE_1)
    attributes: TITULAR char(5), NOMBRE char(250), FIRME char(5), LOCALIDAD char(80), TIPO_TRAMO char(5), FUENTE_V char(5), NOMBRE_CAT char(250), TIPO_VIAL char(5), DGC_VIA char(19), SITUACION char(5), FECHA_ALTA char(8), ID_VIAL char(15), ORDEN char(5), ID_Fenomen char(5), CLASE char(5), SENTIDO char(5), TIPO_VEHIC char(20), VELOCIDAD char(5), TIPO char(5), ESTADOFIS char(5), FECHA_BAJA char(8), ESTADO char(5), CODIGO char(15), ORIGEN_Z char(5), NCARRILES char(5), VIA char(5), CLASIF char(5), CALZADA char(5), ACCESO char(5), NOMBRE_ALT char(250),
      ID_TRAMO char(15), ANCHOCS char(5), ID_HOJA char(5), ITINERANCIA char(20)
FeatureJoiner_13
    ATTR_CONFLICT_RES = Use Left
    GEOMETRY_HANDLING = Use Left
    JOIN_KEYS = igds_level_name SBM_Names AUTO
    JOIN_MODE = Inner
    JOINED -> Tester_25
    UNJOINED_LEFT -> FeatureJoiner_14 [LEFT]
Tester_25
    BOOL_OP = OR
    COMPOSITE_TEST = 1
    TEST_CLAUSE = TEST @Value(Dataset_Name) = RedViaria_pol_gis
    TEST_MODE = TEST
    PASSED -> Tester_24
Tester_24
    BOOL_OP = OR
    COMPOSITE_TEST = 1
    TEST_CLAUSE = TEST @Value(Is_Border_Attri) = Yes
    TEST_MODE = TEST
    PASSED -> AttributeCreator_26
    FAILED -> GeometryFilter_12
AttributeCreator_26
    ATTR_TABLE = SET_TO igds_level_name = Chk_BOR_@Value(Dataset_Name)_@Value(igds_level_name)
    -> REF_04011_Yard_Garden_Vegetation_Urban_trees_TXT (writer DGNV8_2)
GeometryFilter_12
    BREAK_AGG = No
    GEOM_PORT_NAMES = Point Line Area Text
    POINT -> AttributeCreator_11
    LINE -> AttributeCreator_11
    AREA -> RedViaria_pol (writer GEODATABASE_FILE_1)
    TEXT -> AttributeCreator_11
    <UNFILTERED> -> AttributeCreator_11
AttributeCreator_11
    ATTR_TABLE = SET_TO igds_level_name = Chk_Wrg_Gmetry_@Value(Dataset_Name)_@Value(igds_level_name)
    -> REF_04011_Yard_Garden_Vegetation_Urban_trees_TXT (writer DGNV8_2)
RedViaria_pol (writer GEODATABASE_FILE_1)
    attributes: ID_Fenomen char(5), ID_HOJA char(5), SITUACION char(5), ESTADOFIS char(5), TITULAR char(5), TIPO_TRAMO char(5), ORDEN char(5), NOMBRE char(250), NOMBRE_ALT char(250), ESTADO char(5), TIPO char(5), VIA char(5)
FeatureJoiner_14
    ATTR_CONFLICT_RES = Use Left
    GEOMETRY_HANDLING = Use Left
    JOIN_KEYS = igds_level_name SBM_Names AUTO
    JOIN_MODE = Inner
    JOINED -> Tester_27
    UNJOINED_LEFT -> FeatureJoiner_15 [LEFT]
Tester_27
    BOOL_OP = OR
    COMPOSITE_TEST = 1
    TEST_CLAUSE = TEST @Value(Dataset_Name) = RedViaria_pun_gis
    TEST_MODE = TEST
    PASSED -> Tester_26
Tester_26
    BOOL_OP = OR
    COMPOSITE_TEST = 1
    TEST_CLAUSE = TEST @Value(Is_Border_Attri) = Yes
    TEST_MODE = TEST
    PASSED -> AttributeCreator_24
    FAILED -> GeometryFilter_13
AttributeCreator_24
    ATTR_TABLE = SET_TO igds_level_name = Chk_BOR_@Value(Dataset_Name)_@Value(igds_level_name)
    -> REF_04011_Yard_Garden_Vegetation_Urban_trees_TXT (writer DGNV8_2)
GeometryFilter_13
    BREAK_AGG = No
    GEOM_PORT_NAMES = Point Line Area Text
    LINE -> AttributeCreator_12
    AREA -> AttributeCreator_12
    TEXT -> AttributeCreator_12
    <UNFILTERED> -> AttributeCreator_12
AttributeCreator_12
    ATTR_TABLE = SET_TO igds_level_name = Chk_Wrg_Gmetry_@Value(Dataset_Name)_@Value(igds_level_name)
    -> REF_04011_Yard_Garden_Vegetation_Urban_trees_TXT (writer DGNV8_2)
FeatureJoiner_15
    ATTR_CONFLICT_RES = Use Left
    GEOMETRY_HANDLING = Use Left
    JOIN_KEYS = igds_level_name SBM_Names AUTO
    JOIN_MODE = Inner
    JOINED -> Tester_29
    UNJOINED_LEFT -> FeatureJoiner_16 [LEFT]
Tester_29
    BOOL_OP = OR
    COMPOSITE_TEST = 1
    TEST_CLAUSE = TEST @Value(Dataset_Name) = Hidrografia_lin_gis
    TEST_MODE = TEST
    PASSED -> Tester_28
Tester_28
    BOOL_OP = OR
    COMPOSITE_TEST = 1 OR 2
    TEST_CLAUSE:
      TEST @Value(Is_Border_Attri) = Yes
      TEST @Value(COMPONEN1D) = BOR
    TEST_MODE = TEST
    PASSED -> AttributeCreator_25
    FAILED -> GeometryFilter_14
AttributeCreator_25
    ATTR_TABLE = SET_TO igds_level_name = Chk_BOR_@Value(Dataset_Name)_@Value(igds_level_name)
    -> REF_04011_Yard_Garden_Vegetation_Urban_trees_TXT (writer DGNV8_2)
GeometryFilter_14
    BREAK_AGG = No
    GEOM_PORT_NAMES = Point Line Area Text
    POINT -> AttributeCreator_13
    LINE -> Hidrografia_lin (writer GEODATABASE_FILE_1)
    AREA -> AttributeCreator_13
    TEXT -> AttributeCreator_13
    <UNFILTERED> -> AttributeCreator_13
AttributeCreator_13
    ATTR_TABLE = SET_TO igds_level_name = Chk_Wrg_Gmetry_@Value(Dataset_Name)_@Value(igds_level_name)
    -> REF_04011_Yard_Garden_Vegetation_Urban_trees_TXT (writer DGNV8_2)
Hidrografia_lin (writer GEODATABASE_FILE_1)
    attributes: SITUACION char(5), CUENCA char(10), CLASIF char(5), CANALIZ char(5), ESTADO char(5), COMPONEN1D char(5), SUBCUENCA char(250), ID_HOJA char(5), NOMBRE char(250), NIVEL char(5), ID_Fenomen char(5), REGIMEN char(5), TIPO char(5)
FeatureJoiner_16
    ATTR_CONFLICT_RES = Use Left
    GEOMETRY_HANDLING = Use Left
    JOIN_KEYS = igds_level_name SBM_Names AUTO
    JOIN_MODE = Inner
    JOINED -> Tester_31
    UNJOINED_LEFT -> FeatureJoiner_17 [LEFT]
Tester_31
    BOOL_OP = OR
    COMPOSITE_TEST = 1
    TEST_CLAUSE = TEST @Value(Dataset_Name) = Hidrografia_pol_gis
    TEST_MODE = TEST
    PASSED -> Tester_30
Tester_30
    BOOL_OP = OR
    COMPOSITE_TEST = 1
    TEST_CLAUSE = TEST @Value(Is_Border_Attri) = Yes
    TEST_MODE = TEST
    PASSED -> AttributeCreator_23
    FAILED -> GeometryFilter_15
AttributeCreator_23
    ATTR_TABLE = SET_TO igds_level_name = Chk_BOR_@Value(Dataset_Name)_@Value(igds_level_name)
    -> REF_04011_Yard_Garden_Vegetation_Urban_trees_TXT (writer DGNV8_2)
GeometryFilter_15
    BREAK_AGG = No
    GEOM_PORT_NAMES = Point Line Area Text
    POINT -> AttributeCreator_14
    LINE -> AttributeCreator_14
    AREA -> Hidrografia_pol (writer GEODATABASE_FILE_1)
    TEXT -> AttributeCreator_14
    <UNFILTERED> -> AttributeCreator_14
AttributeCreator_14
    ATTR_TABLE = SET_TO igds_level_name = Chk_Wrg_Gmetry_@Value(Dataset_Name)_@Value(igds_level_name)
    -> REF_04011_Yard_Garden_Vegetation_Urban_trees_TXT (writer DGNV8_2)
Hidrografia_pol (writer GEODATABASE_FILE_1)
    attributes: SITUACION char(5), CUENCA char(10), CLASIF char(5), CANALIZ char(5), ESTADO char(5), ID_HOJA char(5), NOMBRE char(250), NIVEL char(5), TIPO char(5), SUBCUENCA char(250), REGIMEN char(5), ID_Fenomen char(5)
FeatureJoiner_17
    ATTR_CONFLICT_RES = Use Left
    GEOMETRY_HANDLING = Use Left
    JOIN_KEYS = igds_level_name SBM_Names AUTO
    JOIN_MODE = Inner
    JOINED -> Tester_33
    UNJOINED_LEFT -> FeatureJoiner_18 [LEFT]
Tester_33
    BOOL_OP = OR
    COMPOSITE_TEST = 1
    TEST_CLAUSE = TEST @Value(Dataset_Name) = Hidrografia_pun_gis
    TEST_MODE = TEST
    PASSED -> Tester_32
Tester_32
    BOOL_OP = OR
    COMPOSITE_TEST = 1
    TEST_CLAUSE = TEST @Value(Is_Border_Attri) = Yes
    TEST_MODE = TEST
    PASSED -> AttributeCreator_22
    FAILED -> GeometryFilter_16
AttributeCreator_22
    ATTR_TABLE = SET_TO igds_level_name = Chk_BOR_@Value(Dataset_Name)_@Value(igds_level_name)
    -> REF_04011_Yard_Garden_Vegetation_Urban_trees_TXT (writer DGNV8_2)
GeometryFilter_16
    BREAK_AGG = No
    GEOM_PORT_NAMES = Point Line Area Text
    POINT -> Hidrografia_pun (writer GEODATABASE_FILE_1)
    LINE -> AttributeCreator_15
    AREA -> AttributeCreator_15
    TEXT -> AttributeCreator_15
    <UNFILTERED> -> AttributeCreator_15
AttributeCreator_15
    ATTR_TABLE = SET_TO igds_level_name = Chk_Wrg_Gmetry_@Value(Dataset_Name)_@Value(igds_level_name)
    -> REF_04011_Yard_Garden_Vegetation_Urban_trees_TXT (writer DGNV8_2)
Hidrografia_pun (writer GEODATABASE_FILE_1)
    attributes: objectid integer, ID_Fenomen char(254), ID_HOJA char(5), NOMBRE char(250), TIPO char(3)
FeatureJoiner_18
    ATTR_CONFLICT_RES = Use Left
    GEOMETRY_HANDLING = Use Left
    JOIN_KEYS = igds_level_name SBM_Names AUTO
    JOIN_MODE = Inner
    JOINED -> Tester_35
    UNJOINED_LEFT -> FeatureJoiner_19 [LEFT]
Tester_35
    BOOL_OP = OR
    COMPOSITE_TEST = 1
    TEST_CLAUSE = TEST @Value(Dataset_Name) = EdiPobCons_lin_gis
    TEST_MODE = TEST
    PASSED -> Tester_34
Tester_34
    BOOL_OP = OR
    COMPOSITE_TEST = 1
    TEST_CLAUSE = TEST @Value(Is_Border_Attri) = Yes
    TEST_MODE = TEST
    PASSED -> AttributeCreator_21
    FAILED -> GeometryFilter_17
AttributeCreator_21
    ATTR_TABLE = SET_TO igds_level_name = Chk_BOR_@Value(Dataset_Name)_@Value(igds_level_name)
    -> REF_04011_Yard_Garden_Vegetation_Urban_trees_TXT (writer DGNV8_2)
GeometryFilter_17
    BREAK_AGG = No
    GEOM_PORT_NAMES = Point Line Area Text
    POINT -> AttributeCreator_16
    LINE -> EdiPobCons_lin (writer GEODATABASE_FILE_1)
    AREA -> AttributeCreator_16
    TEXT -> AttributeCreator_16
    <UNFILTERED> -> AttributeCreator_16
AttributeCreator_16
    ATTR_TABLE = SET_TO igds_level_name = Chk_Wrg_Gmetry_@Value(Dataset_Name)_@Value(igds_level_name)
    -> REF_04011_Yard_Garden_Vegetation_Urban_trees_TXT (writer DGNV8_2)
EdiPobCons_lin (writer GEODATABASE_FILE_1)
    attributes: ID_Fenomen char(5), ID_HOJA char(5), TIPO char(5), ESTADO char(5), BIC char(5), CLASIF char(5), SITUACION char(5), USO char(5), NOMBRE char(250)
FeatureJoiner_19
    ATTR_CONFLICT_RES = Use Left
    GEOMETRY_HANDLING = Use Left
    JOIN_KEYS = igds_level_name SBM_Names AUTO
    JOIN_MODE = Inner
    JOINED -> Tester_37
    UNJOINED_LEFT -> FeatureJoiner_20 [LEFT]
Tester_37
    BOOL_OP = OR
    COMPOSITE_TEST = 1
    TEST_CLAUSE = TEST @Value(Dataset_Name) = EdiPobCons_pol_gis
    TEST_MODE = TEST
    PASSED -> Tester_36
Tester_36
    BOOL_OP = OR
    COMPOSITE_TEST = 1
    TEST_CLAUSE = TEST @Value(Is_Border_Attri) = Yes
    TEST_MODE = TEST
    PASSED -> AttributeCreator_20
    FAILED -> GeometryFilter_18
AttributeCreator_20
    ATTR_TABLE = SET_TO igds_level_name = Chk_BOR_@Value(Dataset_Name)_@Value(igds_level_name)
    -> REF_04011_Yard_Garden_Vegetation_Urban_trees_TXT (writer DGNV8_2)
GeometryFilter_18
    BREAK_AGG = No
    GEOM_PORT_NAMES = Point Line Area Text
    POINT -> AttributeCreator_17
    LINE -> AttributeCreator_17
    AREA -> EdiPobCons_pol (writer GEODATABASE_FILE_1)
    TEXT -> AttributeCreator_17
    <UNFILTERED> -> AttributeCreator_17
AttributeCreator_17
    ATTR_TABLE = SET_TO igds_level_name = Chk_Wrg_Gmetry_@Value(Dataset_Name)_@Value(igds_level_name)
    -> REF_04011_Yard_Garden_Vegetation_Urban_trees_TXT (writer DGNV8_2)
EdiPobCons_pol (writer GEODATABASE_FILE_1)
    attributes: ID_Fenomen char(5), ESTADO char(5), ID_HOJA char(5), TIPO char(5), BIC char(5), CLASIF char(5), NOMBRE char(250), SITUACION char(5), USO char(5), C_NUCLEO_I char(14), D_NUCLEO_I char(80)
FeatureJoiner_20
    ATTR_CONFLICT_RES = Use Left
    GEOMETRY_HANDLING = Use Left
    JOIN_KEYS = igds_level_name SBM_Names AUTO
    JOIN_MODE = Inner
    JOINED -> Tester_39
    UNJOINED_LEFT -> StatisticsCalculator_6
    UNJOINED_LEFT -> AttributeCreator_39
Tester_39
    BOOL_OP = OR
    COMPOSITE_TEST = 1
    TEST_CLAUSE = TEST @Value(Dataset_Name) = EdiPobCons_pun_gis
    TEST_MODE = TEST
    PASSED -> Tester_38
Tester_38
    BOOL_OP = OR
    COMPOSITE_TEST = 1
    TEST_CLAUSE = TEST Is_Border_Attri = Yes
    TEST_MODE = TEST
    PASSED -> AttributeCreator_19
    FAILED -> GeometryFilter_19
AttributeCreator_19
    ATTR_TABLE = SET_TO igds_level_name = Chk_BOR_@Value(Dataset_Name)_@Value(igds_level_name)
    -> REF_04011_Yard_Garden_Vegetation_Urban_trees_TXT (writer DGNV8_2)
GeometryFilter_19
    BREAK_AGG = No
    GEOM_PORT_NAMES = Point Line Area Text
    POINT -> EdiPobCons_pun (writer GEODATABASE_FILE_1)
    LINE -> AttributeCreator_18
    AREA -> AttributeCreator_18
    TEXT -> AttributeCreator_18
    <UNFILTERED> -> AttributeCreator_18
EdiPobCons_pun (writer GEODATABASE_FILE_1)
    attributes: objectid integer, ID_Fenomen char(5), ID_HOJA char(5), NOMBRE char(250), TIPO char(3), VISTO char(3), BIC char(3), CLASIF char(3), ESTADO char(3), SITUACION char(3), USO char(3)
AttributeCreator_18
    ATTR_TABLE = SET_TO igds_level_name = Chk_Wrg_Gmetry_@Value(Dataset_Name)_@Value(igds_level_name)
    -> REF_04011_Yard_Garden_Vegetation_Urban_trees_TXT (writer DGNV8_2)
StatisticsCalculator_6
    COMPUTE_HISTOGRAM = NO
    COUNT_ATTR = _count
    GROUP_BY = igds_level_name
    MAX_ATTR = _max
    MEAN_ATTR = _mean
    MIN_ATTR = _min
    PREPEND_ATTR_NAME_CHOICE = For multiple results only
    STATS_ATTRS = igds_level_name
    SUM_ATTR = _sum
AttributeCreator_39
    ATTR_TABLE = SET_TO igds_level_name = Chk_Not_Imported_GDB_@Value(igds_level_name)
    -> REF_04011_Yard_Garden_Vegetation_Urban_trees_TXT (writer DGNV8_2)
REF_04011_Yard_Garden_Vegetation_Urban_trees_TXT (writer DGNV8_2)

Bookmark: Reference_Files
LimiteAdministrativo_lin (reader ESRISHAPE_1)
    attributes: ID_Fenomen char(5), CODINE1 long, CODINE2 long, ENCLAVE1 long, ENCLAVE2 long, ID_LINLIM char(43), MUN1 char(250), MUN2 char(250), TIPO char(3), URL_RESOUR char(250)
    -> LimiteAdministrativo_lin (writer GEODATABASE_FILE_1)
PuntosGeodesicos_pun (reader ESRISHAPE_1)
    attributes: ID_Fenomen char(5), ASTRONOMIC char(8), FECHACALC char(8), GRAVEDAD char(3), H_ORTO float, ID_HOJA char(5), IDCALC char(10), IDENTIFICA char(10), NOMBRE char(254), ORGANISMOC char(250), REDGEODESI char(3), REDNIVELAC char(3), TITULAR char(3)
    -> PuntosGeodesicos_pun (writer GEODATABASE_FILE_1)
RedViaria_pun (reader ESRISHAPE_1)
    attributes: ID_Fenomen char(5), EXTENSION char(20), FECHA ALTA date, FUENTE char(40), ID_VIARIA long, ID_PORPK number(20,0), ID_TRAMO number(20,0), ID_VIAL number(20,0), NUMERO number(20,0), SENTIDO_PK char(3), TIPO_PORPK char(15)
    -> RedViaria_pun (writer GEODATABASE_FILE_1)
Cuadricula_5k_pol (reader ESRISHAPE_1)
    attributes: ID_Fenomen char(5), CF_50K char(3), CF_5K char(5), HUSO long, ID_HOJA char(5), NOMBRE char(250)
    -> Cuadricula_5k_pol (writer GEODATABASE_FILE_1)
PuntosGNSS_pun (reader ESRISHAPE_1)
    attributes: OBJECTID long, ID_Fenomen char(5), COD_IERS char(9), ID_HOJA char(5), IDENTIFICA char(10), RDIS char(250), RED_EPN char(3), RTK char(3), TITULAR char(3)
    -> PuntosGNSS_pun (writer GEODATABASE_FILE_1)
Redferro_pun (reader ESRISHAPE_1)
    attributes: objectid long, ID_Fenomen char(5), EXTENSION char(20), FECHA_ALTA char(8), FUENTE char(40), ID_FERRO char(20), ID_PORPK char(20), ID_TRAMO char(20), ID_VIAL char(20), NUMERO double, ID_HOJA char(5)
    -> RedFerro_pol (writer GEODATABASE_FILE_1)

Bookmark: Not_required
NomGeo_lin (writer GEODATABASE_FILE_1)
    attributes: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
NomGeo_pun (writer GEODATABASE_FILE_1)
    attributes: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

Bookmark: Add the ID HOJA
AttributeCreator_40
    ATTR_TABLE = SET_TO ID_HOJA
    -> FeatureJoiner [LEFT]

Bookmark: New Bookmark
Tester_40
    BOOL_OP = OR
    COMPOSITE_TEST = 1
    TEST_CLAUSE = TEST @Value(igds_level_name) = 08003_Enegy_Install_Infra_Laying_Tower_Ln
    TEST_MODE = TEST
    PASSED -> AttributeManager
    FAILED -> FeatureJoiner_10 [LEFT]
AttributeManager
    ATTR_TABLE = SET_TO igds_level_name = 08003_Enegy_Install_Infra_Laying_Tower_Pnt
    -> FeatureJoiner_11 [LEFT]
