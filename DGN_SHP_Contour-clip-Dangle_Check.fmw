FME workspace DGN_SHP_Contour-clip-Dangle_Check.fmw

Parameters:
- DestDataset_DGNV8 =
- DestDataset_SHAPEFILE =
- DestDataset_SHAPEFILE_2 =
- FEATURE_TYPES =
- FEATURE_TYPES_2 =
- FEATURE_TYPES_3 =
- SourceDataset_DGNV8 =
- SourceDataset_DGNV8_4 =
- SourceDataset_DGNV8_5 =

Readers:
- DGNV8_1: DGNV8 from $(SourceDataset_DGNV8)
- DGNV8_2: DGNV8 from $(SourceDataset_DGNV8_5)
- DGNV8_3: DGNV8 from $(SourceDataset_DGNV8_4)

Writers:
- SHAPEFILE_1: SHAPEFILE to $(DestDataset_SHAPEFILE_2)
- SHAPEFILE_3: SHAPEFILE to $(DestDataset_SHAPEFILE) in EPSG:26916
- DGNV8_4: DGNV8 to $(DestDataset_DGNV8)

GeometryFilter
    BREAK_AGG = No
    GEOM_PORT_NAMES = Area Text
    <UNFILTERED> -> AttributeCreator_8
    AREA -> SpatialFilter [Candidate]
    TEXT -> SpatialFilter [Filter]
SpatialFilter
    AGGREGATE_HANDLING = Yes
    ATTR_ACCUM_MODE = Prefix Filter
    ATTR_PREFIX = _TexT_
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_2
    FAILED -> AttributeCreator_9
    <REJECTED> -> AttributeCreator_9
AttributeCreator_2
    ATTR_TABLE = SET_TO Tile_Index = @Value(_TexT_fme_text_string)
    -> Clipper_2 [CLIPPER]
AttributeCreator_9
    ATTR_TABLE = SET_TO Errors_Comment = Wrong_DGN_TILE_POLY_TEXT_Mismatch_In_Tile_Index
    -> Junction
AttributeCreator_8
    ATTR_TABLE = SET_TO Errors_Comment = Wrong_DGN_Geometry_Type_in_Tile_Index
    -> Junction
Counter
    CNT_ATTR = _count
    DOMAIN = counter
    SCOPE = Global
    START = 0
    -> Tester_4
Tester_4
    BOOL_OP = OR
    COMPOSITE_TEST = 1 OR 2 OR 3 OR 4
    TEST_CLAUSE:
      TEST @Value(igds_level_name) = IND-DEP
      TEST @Value(igds_level_name) = INDEX-CONTOUR
      TEST @Value(igds_level_name) = INT-CONTOUR
      TEST @Value(igds_level_name) = INT-DEP
    TEST_MODE = TEST
    PASSED -> Clipper [CLIPPEE]
    FAILED -> AttributeCreator_7
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Clipper_2 [CLIPPEE]
Clipper_2
    ATTR_ACCUM_MODE = Prefix Clipper
    BOUNDARY_CASES = Treat as Inside
    CLEANING_TOLERANCE = Automatic
    CLIPPED_ATTR = _clipped
    CLIPPER_PREFIX = 1_
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> NodeValence [Line]
    INSIDE -> CoordinateRounder
    <REJECTED> -> Junction
CoordinateRounder
    XPREC = 3
    YPREC = 3
    ZPREC = 0
    ROUNDED -> Tester_2
Tester_2
    BOOL_OP = OR
    COMPOSITE_TEST = 1 OR 2
    TEST_CLAUSE:
      TEST @Value(igds_level_name) = INT-CONTOUR
      TEST @Value(igds_level_name) = INT-DEP
    TEST_MODE = TEST
    PASSED -> AttributeCreator_3
    FAILED -> Tester_3
Tester_3
    BOOL_OP = OR
    COMPOSITE_TEST = 1 OR 2
    TEST_CLAUSE:
      TEST @Value(igds_level_name) = INDEX-CONTOUR
      TEST @Value(igds_level_name) = IND-DEP
    TEST_MODE = TEST
    PASSED -> AttributeCreator_4
AttributeCreator_4
    ATTR_TABLE:
      SET_TO igds_color.blue = 0
      SET_TO igds_color.green = 127
      SET_TO igds_color.red = 255
    -> BoundsExtractor_2
BoundsExtractor_2
    XMAX = _xmax
    XMIN = _xmin
    YMAX = _ymax
    YMIN = _ymin
    ZMAX = _zmax
    ZMIN = _zmin
    -> Tester
Tester
    BOOL_OP = OR
    COMPOSITE_TEST = 1
    TEST_CLAUSE = TEST @Value(_zmax) = @Value(_zmin)
    TEST_MODE = TEST
    PASSED -> AttributeCreator_5
    FAILED -> AttributeCreator_15
AttributeCreator_5
    ATTR_TABLE:
      SET_TO LINE_STYLE = Solid
      SET_TO LINE_COLOR = RGB(@Value(igds_color.red),@Value(igds_color.green),@Value(igds_color.blue))
      SET_TO LINE_WIDTH = 1
      SET_TO ELEVATION = @Value(_zmin)
      SET_TO LAYER = @Value(igds_level_name)
    -> AttributeCreator
AttributeCreator_3
    ATTR_TABLE:
      SET_TO igds_color.blue = 0
      SET_TO igds_color.green = 87
      SET_TO igds_color.red = 135
    -> BoundsExtractor
BoundsExtractor
    XMAX = _xmax
    XMIN = _xmin
    YMAX = _ymax
    YMIN = _ymin
    ZMAX = _zmax
    ZMIN = _zmin
    -> Tester_5
Tester_5
    BOOL_OP = OR
    COMPOSITE_TEST = 1
    TEST_CLAUSE = TEST @Value(_zmax) = @Value(_zmin)
    TEST_MODE = TEST
    PASSED -> AttributeCreator_6
    FAILED -> AttributeCreator_15
AttributeCreator_6
    ATTR_TABLE:
      SET_TO LINE_STYLE = Solid
      SET_TO LINE_COLOR = RGB(@Value(igds_color.red),@Value(igds_color.green),@Value(igds_color.blue))
      SET_TO LINE_WIDTH = 1
      SET_TO ELEVATION = @Value(_zmin)
      SET_TO LAYER = @Value(igds_level_name)
    -> AttributeCreator
AttributeCreator
    ATTR_TABLE = SET_TO Tile_Name_Clipped = @Value(1__TexT_fme_text_string)
    -> No-Dong (writer SHAPEFILE_3)
No-Dong (writer SHAPEFILE_3)
    attributes: LAYER varchar(13), ELEVATION number(20,0), LINE_STYLE varchar(5), LINE_COLOR varchar(14), LINE_WIDTH long
AttributeCreator_15
    ATTR_TABLE = SET_TO Errors_Comment = Err_contour-height-check
    -> Junction_2
NodeValence
    Node -> TestFilter
TestFilter
    DEFAULT_VALUE = MORE_SNAP_LINE_POINTS
    TEST_LIST = "BOOL_OP,OR,COMPOSITE_TEST,""""""1"""""",TEST_CLAUSE,TEST @Value(valence) = 1",DANGLING_END_POINT,"BOOL_OP,OR,COMPOSITE_TEST,""""""1"""""",TEST_CLAUSE,TEST @Value(valence) = 2",Psedo_NODE_POINT,"BOOL_OP,OR,COMPOSITE_TEST,""""""1"""""",TEST_CLAUSE,TEST @Value(valence) = 3",Tee_JUNCTION_POINT,"BOOL_OP,OR,COMPOSITE_TEST,""""""1"""""",TEST_CLAUSE,TEST @Value(valence) = 4",INTERSECTION_POINT
    MORE_SNAP_LINE_POINTS -> AttributeCreator_14
    DANGLING_END_POINT -> AttributeCreator_10
    Psedo_NODE_POINT -> AttributeCreator_11
    Tee_JUNCTION_POINT -> AttributeCreator_12
    INTERSECTION_POINT -> AttributeCreator_13
AttributeCreator_10
    ATTR_TABLE = SET_TO Errors_Comment = Vertex_DANGLING_END_POINT
    -> Junction_2
AttributeCreator_11
    ATTR_TABLE = SET_TO Errors_Comment = Vertex_Psedo_NODE_POINT
    -> Junction_2
AttributeCreator_12
    ATTR_TABLE = SET_TO Errors_Comment = Vertex_Tee_JUNCTION_POINT
    -> Junction_2
AttributeCreator_13
    ATTR_TABLE = SET_TO Errors_Comment = Vertex_INTERSECTION_POINT
    -> Junction_2
AttributeCreator_14
    ATTR_TABLE = SET_TO Errors_Comment = Vertex_More_Multiple_Points
    -> Junction_2
AttributeCreator_7
    ATTR_TABLE = SET_TO Errors_Comment = Wrong_DGN_LEVEL_Name
    -> Junction
Junction
    -> Junction_2
Junction_2
    -> Shapefile1 (writer SHAPEFILE_1)
    -> Level1 (writer DGNV8_4)
Shapefile1 (writer SHAPEFILE_1)
    attributes: Errors_Com varchar(200)
Level1 (writer DGNV8_4)
    attributes: Errors_Comment char(200), arc_id char(20), node_id char(20), valence char(20), _count char(20), fme_rejection_code string, Tile_Index string, _TexT_fme_feature_type char(50), _TexT_fme_text_string string, _TexT_fme_rotation double, _TexT_fme_text_size double, _predicate string, _clipped char(3), igds_color.blue char(200), igds_color.green char(200), igds_color.red char(200), 1_Tile_Index string, 1__TexT_fme_feature_type char(50), 1__TexT_fme_text_string string, 1__TexT_fme_rotation double, 1__TexT_fme_text_size double, 1_fme_feature_type char(50), 1__predicate string, _xmax double, _xmin double, _ymax double, _ymin double, _zmax double, _zmin double

Bookmark: Tile_Index
Default (reader DGNV8_2)
    -> GeometryFilter

Bookmark: AOI
Default (reader DGNV8_3)
    -> Clipper [CLIPPER]

Bookmark: Contours
INT-CONTOUR (reader DGNV8_1)
    -> Counter

FME custom transformer NodeValence
Notes
    This transformer builds arc-node topology in attributes to mimic
    ARC/INFO
    Coverage network topology and adds 
    valence
    . See 
        topology_basics
    for some good diagrams and further discussion. After editing or filtering this process needs to be rerun, just like an
    ARC/INFO Build
    command to rebuild the correct relationships with new feature counts. The original system keys all ended in "#". The topology stack was stored as a series of layers inside a single dataset called a
    coverage
    .
    The lines have topology attributes exposed in the
    AAT
    table and nodes have attributes in the 
    NAT
    table, hence the suffix names 
    _aat
    and 
    _nat
    . The two featuretypes (lines and points) are intended to be considered as a single set. Not included in the
    AAT
    table is polygon topology which would contain the LPOLY# and RPOLY# identifiers.
    This process includes the equivalent of
    CLEAN
    which breaks all arcs at junctions, explodes all multiparts, removes all coincident lines and vertices.
    The addition of a 
    valence
    to the 
    NAT
    table is useful for analysis to classify
    dangles
    (1),
    pseudonodes
    (2),
    tees
    (3),
    intersections
    (4) or
    multiple junctions 
    (>4)
    .
    The arcs (lines) contain a foreign key to the 
    node_id
    in the 
    fnode
    and 
    tnode
    attributes to allow arcs to be tested for 
    direction 
    relative to the nodes.
    * Indexing the keys will be essential for reasonable performance when selecting or joining these two tables. Indexing in 
    ARC/INFO
    is implied because the original keys with a "#" in the name are the record number similiar to OBJECTID.
    * Tolerance defaults to 0.1 metre
    * The 
    arc_id
    is just one of the arcs joining the node as in the original model.
    * If arcs are not already split they will be split and therefore will duplicate existing attributes.
    * The fme_feature_ type is used to name the outputs the same as the source featuretype with a suffix _aat and _nat
Input is a branched polyline network <ft>
    Output is a cleaned line featuretype <ft>_aat and point representing nodes <ft>_nat
lines (PK arc_id) have fnode_id and tnode_id
nodes have node_id and valence and arc_id as first connecting arc
    Valence is a count of the number of arcs connecting at a node.

Note: Notes / This transformer builds arc-node topology in attributes to mimic ARC/INFO Coverage network topology and adds valence. See topology_basics for some good diagrams and further discussion. After editing or filtering this process needs to be rerun, just like an ARC/INFO Build command to rebuild the correct relationships with new feature counts. The original system keys all ended in "#". The topology stack was stored as a series of layers inside a single dataset called a coverage. / The lines have topology attributes exposed in the AAT table and nodes have attributes in the NAT table, hence the suffix names _aat and _nat. The two featuretypes (lines and points) are intended to be considered as a single set. Not included in the AAT table is polygon topology which would contain the LPOLY# and RPOLY# identifiers. / This process includes the equivalent of CLEAN which breaks all arcs at junctions, explodes all multiparts, removes all coincident lines and vertices. / The addition of a valence to the NAT table is useful for analysis to classify dangles (1), pseudonodes (2), tees (3), intersections (4) or multiple junctions (>4). / The arcs (lines) contain a foreign key to the node_id in the fnode and tnode attributes to allow arcs to be tested for direction relative to the nodes. / * Indexing the keys will be essential for reasonable performance when selecting or joining these two tables. Indexing in ARC/INFO is implied because the original keys with a "#" in the name are the record number similiar to OBJECTID. / * Tolerance defaults to 0.1 metre / * The arc_id is just one of the arcs joining the node as in the original model. / * If arcs are not already split they will be split and therefore will duplicate existing attributes. / * The fme_feature_ type is used to name the outputs the same as the source featuretype with a suffix _aat and _nat
Line (input)
    -> AttributeExposer

Bookmark: New Bookmark
Note: Splits arcs if not already split at intersections before assigning unique IDs which is transferred to the node. / Creates a point at every intersection and ends of every arc. Does not duplicate points at common junctions thank goodness / Adds a list of arcs connected to each node for the valence calculator
AttributeExposer
    ATTR_LIST = fme_feature_type
    -> First_Intersector
First_Intersector: Intersector
    DUPLICATE_Z_NODES = No
    LIST_NAME = all_reaches
    OV_ATTR = _overlaps
    PERFORM_SELF_INTERSECTION = No
    SEG_ATTR = _segments
    SEPARATE_COLLINEAR_SEGMENTS = No
    INTERSECTED -> arc_id_counter
arc_id_counter: Counter
    CNT_ATTR = arc_id
    DOMAIN = counter
    SCOPE = Local
    START = 1
    -> Intersector
Intersector
    DUPLICATE_Z_NODES = No
    LIST_NAME = all_reaches
    OV_ATTR = _overlaps
    PERFORM_SELF_INTERSECTION = No
    SEG_ATTR = _segments
    SEPARATE_COLLINEAR_SEGMENTS = No
    INTERSECTED -> Snipper_Begin
    INTERSECTED -> FeatureMerger_2 [REQUESTOR]
    NODE -> Node_id_counter

Bookmark: Distinguish between FNODE and TNODE (NeighborhoodPair does not)
Note: Snipper gets the first and last points. / Geohash is a spatial key to test for spatial coincidence with the nodes
Snipper_Begin
    ENDVERTEXATTR = 0
    SNIPMODE = Vertex
    STARTVERTEXATTR = 0
    -> Geohash_Begin
    REMNANTS -> Snipper_End
Geohash_Begin: GeometryExtractor
    ATTR = from_geohash
    GEOHASH_PRECISION_DISPLAY = ~9.3 mm (12 characters)
    KIND_LONG = Geohash
    OGC_WKT_PRECISION_DISPLAY = Shortened 64-bit
    -> FeatureMerger [REQUESTOR]
Snipper_End
    ENDVERTEXATTR = -1
    SNIPMODE = Vertex
    STARTVERTEXATTR = -1
    -> Geohash_End
Geohash_End: GeometryExtractor
    ATTR = to_geohash
    GEOHASH_PRECISION_DISPLAY = ~9.3 mm (12 characters)
    KIND_LONG = Geohash
    OGC_WKT_PRECISION_DISPLAY = Shortened 64-bit
    -> FeatureMerger_3 [REQUESTOR]
Geohash_node: GeometryExtractor
    ATTR = node_geohash
    GEOHASH_PRECISION_DISPLAY = ~9.3 mm (12 characters)
    KIND_LONG = Geohash
    OGC_WKT_PRECISION_DISPLAY = Shortened 64-bit
    -> FeatureMerger [SUPPLIER]
    -> FeatureMerger_3 [SUPPLIER]

Bookmark: Add node_id and valence
Node_id_counter: Counter
    CNT_ATTR = node_id
    DOMAIN = counter2
    SCOPE = Local
    START = 1
    -> ListElementCounter
Note: Valence
ListElementCounter
    CNT_ATTR = valence
    LIST_NAME = all_reaches{}
    -> AttributeKeeper
    -> Geohash_node
Note: Calculates the valence from the hidden list of arc-ids. / Output the nodes with unique ids. / arc_id is simply one of the connected arcs.
AttributeKeeper
    CREATE_BULK_MODE_FEATURES = No
    KEEP_ATTRS = arc_id,network_id,node_id,valence,fme_feature_type
    -> Node (output)

Bookmark: From Node
FeatureMerger
    ATTR_ACCUM_MODE = Merge Supplier
    ATTR_CONFLICT_RES = Use Requestor
    IGNORE_NULLS = No
    JOIN_KEYS = @Value(from_geohash) @Value(node_geohash) AUTO
    MERGE_TYPE = Attributes Only
    PROCESS_DUPS = No
    SUPPLIERS_FIRST = No
    MERGED -> AttributeCreator
Note: Join back the node_id as the from-node based on a Geohash match
AttributeCreator
    ATTR_LIST = fnode_id,@Value(node_id)
    -> AttributeKeeper_2
AttributeKeeper_2
    CREATE_BULK_MODE_FEATURES = No
    KEEP_ATTRS = arc_id,fnode_id
    -> FeatureMerger_2 [SUPPLIER]
FeatureMerger_2
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> FeatureMerger_4 [REQUESTOR]

Bookmark: To Node
FeatureMerger_3
    ATTR_ACCUM_MODE = Merge Supplier
    ATTR_CONFLICT_RES = Use Requestor
    IGNORE_NULLS = No
    JOIN_KEYS = @Value(to_geohash) @Value(node_geohash) AUTO
    MERGE_TYPE = Attributes Only
    PROCESS_DUPS = No
    SUPPLIERS_FIRST = No
    MERGED -> AttributeCreator_2
Note: Join back the node_id as the to-node based on a Geohash match
AttributeCreator_2
    ATTR_LIST = tnode_id,@Value(node_id)
    -> AttributeKeeper_3
AttributeKeeper_3
    CREATE_BULK_MODE_FEATURES = No
    KEEP_ATTRS = arc_id,tnode_id
    -> FeatureMerger_4 [SUPPLIER]
FeatureMerger_4
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> AttributeRemover

Bookmark: Tidy temp attributes
AttributeRemover
    LIST_ATTRS = all_reaches{} all_reaches{}.arc_id all_reaches{}.direction all_reaches{}.fme_basename all_reaches{}.ID all_reaches{}.name all_reaches{}.network_id all_reaches{}.OBJECTID all_reaches{}.SHAPE_Length
    REMOVE_ATTRS = _overlaps,_segments
    -> Arc (output)
Arc (output)

Bookmark: Write Nodes
Node (output)
