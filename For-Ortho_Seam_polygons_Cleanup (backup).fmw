FME workspace For-Ortho_Seam_polygons_Cleanup (backup).fmw

Parameters:
- SourceDataset_ESRISHAPE = U:\phee\check.shp   # Source Esri Shapefile(s)
- FEATURE_TYPES = check
- DestDataset_ESRISHAPE = U:\phee\OUT   # Destination Esri Shapefile Folder
- DestDataset_ESRISHAPE_4 = U:\phee\OUT   # Destination Esri Shapefile Folder

Readers:
- ESRISHAPE_1: ESRISHAPE from $(SourceDataset_ESRISHAPE)

Writers:
- ESRISHAPE_2: ESRISHAPE to $(DestDataset_ESRISHAPE)
- ESRISHAPE_3: ESRISHAPE to $(DestDataset_ESRISHAPE_4)

SEAM_POLYGON (reader ESRISHAPE_1)
    attributes: IMG_SUPPOR char(255), SS_ID long
    -> AreaGapAndOverlapCleaner
AreaGapAndOverlapCleaner
    CLEANING_TOLERANCE = Automatic
    CONNECT_Z_MODE = First Wins
    DEAGGREGATE_INPUT = YES
    FILL_ALL_GAPS = Yes
    MEASURE_TYPE = Continuous
    MISSING_VAL_MODE = Compute
    REPAIR_METHOD = Longest Boundary
    REPAIRED -> AreaOnAreaOverlayer [AREA]
    REMNANTS -> Errors_1 (writer ESRISHAPE_3)
    <REJECTED> -> Errors_1 (writer ESRISHAPE_3)
AreaOnAreaOverlayer
    ACCUM_ATTRS_NAME = Use Attributes From One Feature
    CLEANING_TOLERANCE = None
    CONNECT_Z_MODE = First Wins
    DEAGGREGATE_INPUT = Yes
    OVC_ATTR = _overlaps
    AREA -> AreaCalculator
    REMNANTS -> Errors_2 (writer ESRISHAPE_3)
    <REJECTED> -> Errors_2 (writer ESRISHAPE_3)
AreaCalculator
    AREA_ATTR = _area
    AREA_TYPE = Plane Area
    MULT = 1
    -> SEAM_POLYGON (writer ESRISHAPE_2)
    <REJECTED> -> Errors_1 (writer ESRISHAPE_3)
SEAM_POLYGON (writer ESRISHAPE_2)
    attributes: IMG_SUPPOR char(255), SS_ID long, fme_featur char(50), _area double
Errors_1 (writer ESRISHAPE_3)
    attributes: IMG_SUPPOR char(255), SS_ID long, fme_featur char(50)
Errors_2 (writer ESRISHAPE_3)
    attributes: IMG_SUPPOR char(255), SS_ID long, fme_featur char(50)
