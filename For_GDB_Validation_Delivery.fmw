FME workspace For_GDB_Validation_Delivery.fmw

Parameters:
- DestDataset_DGNV8 =
- FEATURE_TYPES =
- SourceDataset_FILEGDB =

Readers:
- FILEGDB_1: FILEGDB from $(SourceDataset_FILEGDB)

Writers:
- DGNV8_1: DGNV8 to $(DestDataset_DGNV8)

Cuadricula_5k_pol (reader FILEGDB_1)
    attributes: OBJECTID objectid, objectid_2 int, ID_Fenomen text(5), CF_50K text(5), CF_5K text(5), HUSO text(20), ID_HOJA text(5), NOMBRE text(250), SHAPE_Length double, SHAPE_Area double, ACCESO text(5), ANCHOCS text(5), BIC text(5), CALZADA text(5), CANALIZ text(5), CLASE text(5), CLASIF text(5), CODEXPLOT text(50), CODIGO text(9), COMPONEN1D text(5), CONTEXTO text(3), COTA text(20), CUENCA text(10), C_NUCLEO_I text(14), DGC_VIA text(19), D_NUCLEO_I text(80), ENERGIA text(3), ESTADO text(3), ESTADOFIS text(5), FECHA_ALTA text(8),
      FECHA_BAJA text(8), FIGURA text(5), FIRME text(5), FUENTE_V text(5), ID_TRAMO text(15), ID_VIAL text(15), ITINERANCI text(20), LOCALIDAD text(80), NCARRILES text(5), NIVEL text(5), NOMBRE_ALT text(250), NOMBRE_CAT text(250), ORDEN text(5), ORIGEN text(20), ORIGEN_Z text(5), PROCEDENCI text(5), REGIMEN text(5), SECCION text(5), SENTIDO text(5), SITUACION text(5), SONDA text(20), SUBCUENCA text(250), TIPO text(5), TIPO_TRAMO text(5), TIPO_VEHIC text(20), TIPO_VIAL text(5), TITULAR text(5), USO text(5), VELOCIDAD text(5), VIA text(5)
    -> Counter
Note: Boundary_Check
Note: Elevation_Point_Check
Note: Contour_Height_Check
Note: Validating_Geometry
Note: For_Vertex_Missing_Issues
Counter
    CNT_ATTR = _COUNT_ID
    DOMAIN = counter
    SCOPE = Global
    START = 1
    -> Tester
    -> GeometryValidator
    -> Tester_3
    -> GeometryFilter
    -> Tester_25
    -> Tester_48
    -> Tester_47
    -> Tester_62
    -> Tester_65
    -> Tester_68
    -> Tester_72
Inspector_2
Note: Road_LINE & Polygon
Note: Hydro_NON_FLAT_Elements
AttributeCreator_28
    ATTR_TABLE = SET_TO igds_level_name = Err_Hydro_CNX_Hidden_@Value(fme_dataset)
    -> Junction_2
Note: Bride
Tester_72
    BOOL_OP = OR
    COMPOSITE_TEST = 1
    TEST_CLAUSE = TEST @Value(fme_feature_type) = CubiertaTer_pol
    TEST_MODE = TEST
    PASSED -> Tester_71
    FAILED -> Tester_73
Tester_73
    BOOL_OP = OR
    COMPOSITE_TEST = 1
    TEST_CLAUSE = TEST @Value(fme_feature_type) = CubiertaTer_lin
    TEST_MODE = TEST
    PASSED -> Tester_74
Tester_74
    BOOL_OP = OR
    COMPOSITE_TEST = 1
    TEST_CLAUSE = TEST @Value(ID_Fenomen) = 12001
    TEST_MODE = TEST
    PASSED -> SpatialFilter_5 [Candidate]
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    FAILED -> AttributeCreator_31
Note: Firewall_Multiple_polygons_Check
Note: Bridge_ELE_CHECK
AttributeCreator_31
    ATTR_TABLE = SET_TO igds_level_name = Err_Firewall_Poly_Missing
    -> Junction
Note: Road-Other_Checks
Junction
    -> Junction_2
Junction_2
    -> Inspector
    -> Level1 (writer DGNV8_1)
Inspector
Level1 (writer DGNV8_1)

Bookmark: New Bookmark
Tester_3
    BOOL_OP = OR
    COMPOSITE_TEST = 1
    TEST_CLAUSE = TEST @Value(fme_feature_type) = Cuadricula_5k_pol
    TEST_MODE = TEST
    PASSED -> Junction_3
    FAILED -> Tester_4
Tester_4
    BOOL_OP = OR
    COMPOSITE_TEST = 1
    TEST_CLAUSE = TEST @Value(fme_feature_type) = CubiertaTer_pol
    TEST_MODE = TEST
    PASSED -> Junction_3
    FAILED -> Tester_5
Tester_5
    BOOL_OP = OR
    COMPOSITE_TEST = 1
    TEST_CLAUSE = TEST @Value(fme_feature_type) = EdiPobCons_pol
    TEST_MODE = TEST
    PASSED -> Tester_51
    FAILED -> Tester_6
Tester_51
    BOOL_OP = OR
    COMPOSITE_TEST = 1 OR 2
    TEST_CLAUSE:
      TEST @Value(TIPO) = MNZ
      TEST @Value(ID_Fenomen) = 04010
    TEST_MODE = TEST
    FAILED -> Junction_3
Tester_6
    BOOL_OP = OR
    COMPOSITE_TEST = 1
    TEST_CLAUSE = TEST @Value(fme_feature_type) = Hidrografia_pol
    TEST_MODE = TEST
    PASSED -> Junction_3
    FAILED -> Tester_7
Tester_7
    BOOL_OP = OR
    COMPOSITE_TEST = 1
    TEST_CLAUSE = TEST @Value(fme_feature_type) = RedFerro_pol
    TEST_MODE = TEST
    PASSED -> Junction_3
    FAILED -> Tester_8
Tester_8
    BOOL_OP = OR
    COMPOSITE_TEST = 1
    TEST_CLAUSE = TEST @Value(fme_feature_type) = RedViaria_pol
    TEST_MODE = TEST
    PASSED -> Junction_3
    FAILED -> Tester_9
Tester_9
    BOOL_OP = OR
    COMPOSITE_TEST = 1
    TEST_CLAUSE = TEST @Value(fme_feature_type) = ServInst_pol
    TEST_MODE = TEST
    PASSED -> Junction_3
Junction_3
    -> AreaOnAreaOverlayer_7 [AREA]
    -> Tester_2
AreaOnAreaOverlayer_7
    ACCUM_ATTRS_NAME = Use Attributes From One Feature
    CLEANING_TOLERANCE = Automatic
    CONNECT_Z_MODE = First Wins
    DEAGGREGATE_INPUT = Yes
    OVC_ATTR = _overlaps
    AREA -> Tester_49
Tester_49
    BOOL_OP = OR
    COMPOSITE_TEST = 1
    TEST_CLAUSE = TEST @Value(_overlaps) = 1
    TEST_MODE = TEST
    PASSED -> AttributeCreator_21
    FAILED -> Tester_50
AttributeCreator_21
    ATTR_TABLE = SET_TO Overlap = Err_GAPS
    -> Junction_4
Tester_50
    BOOL_OP = OR
    COMPOSITE_TEST = 1
    TEST_CLAUSE = TEST @Value(_overlaps) = 2
    TEST_MODE = TEST
    FAILED -> Tester_19
Tester_19
    BOOL_OP = OR
    COMPOSITE_TEST = 1
    TEST_CLAUSE = TEST @Value(_overlaps) < 2
    TEST_MODE = TEST
    FAILED -> AttributeCreator_20
AttributeCreator_20
    ATTR_TABLE = SET_TO Overlap = Err_More_Overlaps
    -> Junction_4
Tester_2
    BOOL_OP = OR
    COMPOSITE_TEST = 1 OR 2
    TEST_CLAUSE:
      TEST @Value(fme_feature_type) = Cuadricula_5k_pol
      TEST @Value(ID_Fenomen) = 04010
    TEST_MODE = TEST
    FAILED -> Dissolver
    FAILED -> AreaOnAreaOverlayer_2 [AREA]
Dissolver
    ACCUM_INPUT_ATTRS = Use Attributes From One Feature
    CLEANING_TOLERANCE = 0.01
    CONNECT_Z_MODE = First Wins
    DEAGGREGATE_INPUT = Yes
    AREA -> AttributeCreator
AttributeCreator
    ATTR_TABLE = SET_TO Outline = Yes
    -> AreaOnAreaOverlayer_2 [AREA]
AreaOnAreaOverlayer_2
    ACCUM_ATTRS_NAME = Use Attributes From One Feature
    CLEANING_TOLERANCE = Automatic
    CONNECT_Z_MODE = First Wins
    DEAGGREGATE_INPUT = Yes
    OVC_ATTR = _overlaps
    AREA -> Tester_10
Tester_10
    BOOL_OP = OR
    COMPOSITE_TEST = 1
    TEST_CLAUSE = TEST @Value(_overlaps) = 1
    TEST_MODE = TEST
    FAILED -> Tester_18
Tester_18
    BOOL_OP = OR
    COMPOSITE_TEST = 1
    TEST_CLAUSE = TEST @Value(_overlaps) <= 2
    TEST_MODE = TEST
    FAILED -> AttributeCreator_4
AttributeCreator_4
    ATTR_TABLE = SET_TO Overlap = Err_More_Overlaps
    -> Junction_4
Junction_4
    -> Inspector_2
    -> Junction_2

Bookmark: Contour_Height_Check
Tester_68
    BOOL_OP = OR
    COMPOSITE_TEST = 1
    TEST_CLAUSE = TEST @Value(fme_feature_type) = Relieve_pun
    TEST_MODE = TEST
    PASSED -> CoordinateRounder
CoordinateRounder
    XPREC = 4
    YPREC = 4
    ZPREC = 3
    ROUNDED -> CoordinateExtractor
CoordinateExtractor
    IND = 0
    MODE = Specify Coordinate
    X_ATTR = _x
    Y_ATTR = _y
    Z_ATTR = _z
    -> Tester_69
Tester_69
    BOOL_OP = OR
    COMPOSITE_TEST = 1
    TEST_CLAUSE = TEST @Value(COTA) = @Value(_z)
    TEST_MODE = TEST
    FAILED -> AttributeCreator_26
AttributeCreator_26
    ATTR_TABLE = SET_TO Diff = @sub(@Value(COTA),@Value(_z))
    -> Tester_70
Tester_70
    BOOL_OP = OR
    COMPOSITE_TEST = 1
    TEST_CLAUSE = NUM_TEST @Value(Diff) RANGE [-0.1,0.1]
    TEST_MODE = TEST
    FAILED -> AttributeCreator_27
AttributeCreator_27
    ATTR_TABLE = SET_TO igds_level_name = Err_COTA_ELE_POINT_Wrong_@Value(fme_feature_type)_@Value(OBJECTID)_OBJ_ID_GDB
    -> Junction_2

Bookmark: Contour_Height_Check
Tester_65
    BOOL_OP = OR
    COMPOSITE_TEST = 1
    TEST_CLAUSE = TEST @Value(fme_feature_type) = Relieve_lin
    TEST_MODE = TEST
    PASSED -> Tester_66
Tester_66
    BOOL_OP = AND
    COMPOSITE_TEST = 1 AND 2
    TEST_CLAUSE:
      TEST @Value(ID_Fenomen) = 03002
      TEST PROCEDENCIA = RES
    TEST_MODE = TEST
    PASSED -> BoundsExtractor
BoundsExtractor
    XMAX = _xmax
    XMIN = _xmin
    YMAX = _ymax
    YMIN = _ymin
    ZMAX = _zmax
    ZMIN = _zmin
    -> AttributeRounder_2
AttributeRounder_2
    PLACES = 3
    ROUND_TYPE = Nearest
    SRC_ATTRS = _zmin
    -> Tester_67
Tester_67
    BOOL_OP = AND
    COMPOSITE_TEST = 1 AND 2
    TEST_CLAUSE:
      TEST @Value(COTA) = @Value(_zmin)
      TEST @Value(COTA) = @Value(_zmax)
    TEST_MODE = TEST
    FAILED -> AttributeCreator_42
AttributeCreator_42
    ATTR_TABLE = SET_TO igds_level_name = Err_Contour_Height_Mismatch_@Value(fme_dataset)
    -> Junction_2

Bookmark: Boundary_Check
Tester
    BOOL_OP = OR
    COMPOSITE_TEST = 1
    TEST_CLAUSE = TEST @Value(fme_feature_type) = Cuadricula_5k_pol
    TEST_MODE = TEST
    PASSED -> Bufferer
    FAILED -> SpatialFilter_6 [Candidate]
Bufferer
    ANGLE = 22.5
    CAP_STYLE = Arc
    CORNER_STYLE = Arc
    MODE = AREA
    OFFSET = 0.001
    OFFSET_UNITS = NONE
    PRECISION = APPROX
    BUFFERED -> SpatialFilter_6 [Filter]
SpatialFilter_6
    AGGREGATE_HANDLING = Yes
    ATTR_ACCUM_MODE = Prefix Filter
    ATTR_PREFIX = _CUD_
    BASE_TYPE = Multiple Filters
    CURVE_BOUNDARY_RULE_PARAM = Default Rule
    PASS_CRITERIA = Pass Against One Filter
    PREDATTR = _predicate
    PREDICATES = CONTAINS
    USE_BOUNDING_BOX = No
    FAILED -> AttributeCreator_2
AttributeCreator_2
    ATTR_TABLE = SET_TO igds_level_name = Err_Outside_5K_Polygon_Data_@Value(fme_feature_type)_@Value(OBJECTID)_OBJ_ID_GDB
    -> Junction_2

Bookmark: Validating_Geometry
GeometryValidator
    ISSUE_ATTR_NAME = _issues
    PRESETS = All
    REPAIR = No
    RULES = AREA_ORIENTATION AREA_ORIENTATION]VALID]FME_CONTROLLER_QUERY_FILE]transformers/dependencies/geometryvalidator8/AREA_ORIENTATION.fme CONSECUTIVE_IDENTICAL_VERTICES_2D CHECK_Z]YES]FME_CONTROLLER_QUERY_FILE]transformers/dependencies/geometryvalidator8/CONSECUTIVE_IDENTICAL_VERTICES_2D.fme MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme OGC_VALID_CHECK OGC_VERSION]V1.2.0]FME_CONTROLLER_QUERY_FILE]transformers/dependencies/geometryvalidator8/OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator8/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator8/SELF_INTERSECTING.fme SHELL_VALIDATION FLIP_APPEARANCE_MODE]FLIP_APPEARANCES]FME_CONTROLLER_QUERY_FILE]transformers/dependencies/geometryvalidator8/SHELL_VALIDATION.fme SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator8/TYPE_REPAIR.fme MISMATCHED_DIMENSIONS FORCE_DIMENSION]2D]FME_CONTROLLER_QUERY_FILE]transformers/dependencies/geometryvalidator8/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator8/MISSING_MEASURES_AND_ELEVATIONS.fme SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    ISSUE_LOCATIONS -> AttributeCreator_3
AttributeCreator_3
    ATTR_TABLE = SET_TO igds_level_name = Err_@Value(issue_found)_@Value(fme_feature_type)_@Value(OBJECTID)_OBJ_ID_GDB
    -> Junction_2

Bookmark: For_Vertex_Missing_Issues
GeometryFilter
    BREAK_AGG = No
    GEOM_PORT_NAMES = Point Line Area
    LINE -> Tester_26
    AREA -> Tester_11
    AREA -> Tester_44
Tester_26
    BOOL_OP = OR
    COMPOSITE_TEST = 1
    TEST_CLAUSE = TEST @Value(fme_feature_type) = Relieve_lin
    TEST_MODE = TEST
    FAILED -> VertexExtractor_13
VertexExtractor_13
    Point -> AttributeCreator_12
AttributeCreator_12
    ATTR_TABLE = SET_TO PoinT_LINE = Yes
    -> PointOnPointOverlayer [POINT]
    -> PointOnPointOverlayer_2 [POINT]
    -> PointOnPointOverlayer_3 [POINT]
    -> PointOnPointOverlayer_4 [POINT]
    -> PointOnPointOverlayer_5 [POINT]
    -> PointOnPointOverlayer_6 [POINT]
Tester_11
    BOOL_OP = OR
    COMPOSITE_TEST = 1
    TEST_CLAUSE = TEST @Value(fme_feature_type) = CubiertaTer_pol
    TEST_MODE = TEST
    PASSED -> VertexExtractor_7
    PASSED -> GeometryCoercer
    FAILED -> Tester_12
VertexExtractor_7
    Point -> PointOnPointOverlayer [POINT]
PointOnPointOverlayer
    DEAGGREGATE_INPUT = Yes
    OV_ATTR = P_overlaps
    TOLERANCE = 0.01
    POINT -> Tester_23
Tester_23
    BOOL_OP = OR
    COMPOSITE_TEST = 1
    TEST_CLAUSE = TEST @Value(PoinT_LINE) = Yes
    TEST_MODE = TEST
    PASSED -> Tester_24
Tester_24
    BOOL_OP = OR
    COMPOSITE_TEST = 1
    TEST_CLAUSE = TEST @Value(P_overlaps) = 0
    TEST_MODE = TEST
    PASSED -> PointOnLineOverlayer_3 [POINT]
GeometryCoercer
    GQUERY:
      for $geom in //geometry
      where $geom/count(parent::geometry) = 0
      return number($geom/@fme_id)
    KIND = fme_line
    COERCED -> PointOnLineOverlayer_3 [LINE]
PointOnLineOverlayer_3
    DEAGGREGATE_INPUT = Yes
    MEASURE_TYPE = Continuous
    MERGE_MEASURES = Yes
    OV_ATTR = PP_overlaps
    TOLERANCE = 0.01
    POINT -> Tester_27
Tester_27
    BOOL_OP = OR
    COMPOSITE_TEST = 1
    TEST_CLAUSE = TEST @Value(PP_overlaps) = 0
    TEST_MODE = TEST
    FAILED -> AttributeCreator_13
AttributeCreator_13
    ATTR_TABLE = SET_TO igds_level_name = Err_Vertex_mismatch_@Value(fme_feature_type)_@Value(OBJECTID)_OBJ_ID_GDB
    -> Junction_2
Tester_12
    BOOL_OP = OR
    COMPOSITE_TEST = 1
    TEST_CLAUSE = TEST @Value(fme_feature_type) = EdiPobCons_pol
    TEST_MODE = TEST
    PASSED -> VertexExtractor_8
    PASSED -> GeometryCoercer_2
    FAILED -> Tester_13
VertexExtractor_8
    Point -> PointOnPointOverlayer_2 [POINT]
PointOnPointOverlayer_2
    DEAGGREGATE_INPUT = Yes
    OV_ATTR = P_overlaps
    TOLERANCE = 0.01
    POINT -> Tester_28
Tester_28
    BOOL_OP = OR
    COMPOSITE_TEST = 1
    TEST_CLAUSE = TEST @Value(PoinT_LINE) = Yes
    TEST_MODE = TEST
    PASSED -> Tester_29
Tester_29
    BOOL_OP = OR
    COMPOSITE_TEST = 1
    TEST_CLAUSE = TEST @Value(P_overlaps) = 0
    TEST_MODE = TEST
    PASSED -> PointOnLineOverlayer_2 [POINT]
GeometryCoercer_2
    GQUERY:
      for $geom in //geometry
      where $geom/count(parent::geometry) = 0
      return number($geom/@fme_id)
    KIND = fme_line
    COERCED -> PointOnLineOverlayer_2 [LINE]
PointOnLineOverlayer_2
    DEAGGREGATE_INPUT = Yes
    MEASURE_TYPE = Continuous
    MERGE_MEASURES = Yes
    OV_ATTR = PP_overlaps
    TOLERANCE = 0.01
    POINT -> Tester_30
Tester_30
    BOOL_OP = OR
    COMPOSITE_TEST = 1
    TEST_CLAUSE = TEST @Value(PP_overlaps) = 0
    TEST_MODE = TEST
    FAILED -> AttributeCreator_14
AttributeCreator_14
    ATTR_TABLE = SET_TO igds_level_name = Err_Vertex_mismatch_@Value(fme_feature_type)_@Value(OBJECTID)_OBJ_ID_GDB
    -> Junction_2
Tester_13
    BOOL_OP = OR
    COMPOSITE_TEST = 1
    TEST_CLAUSE = TEST @Value(fme_feature_type) = Hidrografia_pol
    TEST_MODE = TEST
    PASSED -> VertexExtractor_9
    PASSED -> GeometryCoercer_3
    FAILED -> Tester_14
VertexExtractor_9
    Point -> PointOnPointOverlayer_3 [POINT]
PointOnPointOverlayer_3
    DEAGGREGATE_INPUT = Yes
    OV_ATTR = P_overlaps
    TOLERANCE = 0.01
    POINT -> Tester_31
Tester_31
    BOOL_OP = OR
    COMPOSITE_TEST = 1
    TEST_CLAUSE = TEST @Value(PoinT_LINE) = Yes
    TEST_MODE = TEST
    PASSED -> Tester_32
Tester_32
    BOOL_OP = OR
    COMPOSITE_TEST = 1
    TEST_CLAUSE = TEST @Value(P_overlaps) = 0
    TEST_MODE = TEST
    PASSED -> PointOnLineOverlayer_4 [POINT]
GeometryCoercer_3
    GQUERY:
      for $geom in //geometry
      where $geom/count(parent::geometry) = 0
      return number($geom/@fme_id)
    KIND = fme_line
    COERCED -> PointOnLineOverlayer_4 [LINE]
PointOnLineOverlayer_4
    DEAGGREGATE_INPUT = Yes
    MEASURE_TYPE = Continuous
    MERGE_MEASURES = Yes
    OV_ATTR = PP_overlaps
    TOLERANCE = 0.01
    POINT -> Tester_33
Tester_33
    BOOL_OP = OR
    COMPOSITE_TEST = 1
    TEST_CLAUSE = TEST @Value(PP_overlaps) = 0
    TEST_MODE = TEST
    FAILED -> AttributeCreator_15
AttributeCreator_15
    ATTR_TABLE = SET_TO igds_level_name = Err_Vertex_mismatch_@Value(fme_feature_type)_@Value(OBJECTID)_OBJ_ID_GDB
    -> Junction_2
Tester_14
    BOOL_OP = OR
    COMPOSITE_TEST = 1
    TEST_CLAUSE = TEST @Value(fme_feature_type) = RedFerro_pol
    TEST_MODE = TEST
    PASSED -> VertexExtractor_10
    PASSED -> GeometryCoercer_4
    FAILED -> Tester_15
VertexExtractor_10
    Point -> PointOnPointOverlayer_4 [POINT]
PointOnPointOverlayer_4
    DEAGGREGATE_INPUT = Yes
    OV_ATTR = P_overlaps
    TOLERANCE = 0.01
    POINT -> Tester_34
Tester_34
    BOOL_OP = OR
    COMPOSITE_TEST = 1
    TEST_CLAUSE = TEST @Value(PoinT_LINE) = Yes
    TEST_MODE = TEST
    PASSED -> Tester_35
Tester_35
    BOOL_OP = OR
    COMPOSITE_TEST = 1
    TEST_CLAUSE = TEST @Value(P_overlaps) = 0
    TEST_MODE = TEST
    PASSED -> PointOnLineOverlayer_5 [POINT]
GeometryCoercer_4
    GQUERY:
      for $geom in //geometry
      where $geom/count(parent::geometry) = 0
      return number($geom/@fme_id)
    KIND = fme_line
    COERCED -> PointOnLineOverlayer_5 [LINE]
PointOnLineOverlayer_5
    DEAGGREGATE_INPUT = Yes
    MEASURE_TYPE = Continuous
    MERGE_MEASURES = Yes
    OV_ATTR = PP_overlaps
    TOLERANCE = 0.01
    POINT -> Tester_36
Tester_36
    BOOL_OP = OR
    COMPOSITE_TEST = 1
    TEST_CLAUSE = TEST @Value(PP_overlaps) = 0
    TEST_MODE = TEST
    FAILED -> AttributeCreator_16
AttributeCreator_16
    ATTR_TABLE = SET_TO igds_level_name = Err_Vertex_mismatch_@Value(fme_feature_type)_@Value(OBJECTID)_OBJ_ID_GDB
    -> Junction_2
Tester_15
    BOOL_OP = OR
    COMPOSITE_TEST = 1
    TEST_CLAUSE = TEST @Value(fme_feature_type) = RedViaria_pol
    TEST_MODE = TEST
    PASSED -> VertexExtractor_11
    PASSED -> GeometryCoercer_5
    FAILED -> Tester_16
VertexExtractor_11
    Point -> PointOnPointOverlayer_5 [POINT]
PointOnPointOverlayer_5
    DEAGGREGATE_INPUT = Yes
    OV_ATTR = P_overlaps
    TOLERANCE = 0.01
    POINT -> Tester_37
Tester_37
    BOOL_OP = OR
    COMPOSITE_TEST = 1
    TEST_CLAUSE = TEST @Value(PoinT_LINE) = Yes
    TEST_MODE = TEST
    PASSED -> Tester_38
Tester_38
    BOOL_OP = OR
    COMPOSITE_TEST = 1
    TEST_CLAUSE = TEST @Value(P_overlaps) = 0
    TEST_MODE = TEST
    PASSED -> PointOnLineOverlayer_6 [POINT]
GeometryCoercer_5
    GQUERY:
      for $geom in //geometry
      where $geom/count(parent::geometry) = 0
      return number($geom/@fme_id)
    KIND = fme_line
    COERCED -> PointOnLineOverlayer_6 [LINE]
PointOnLineOverlayer_6
    DEAGGREGATE_INPUT = Yes
    MEASURE_TYPE = Continuous
    MERGE_MEASURES = Yes
    OV_ATTR = PP_overlaps
    TOLERANCE = 0.01
    POINT -> Tester_39
Tester_39
    BOOL_OP = OR
    COMPOSITE_TEST = 1
    TEST_CLAUSE = TEST @Value(PP_overlaps) = 0
    TEST_MODE = TEST
    FAILED -> AttributeCreator_17
AttributeCreator_17
    ATTR_TABLE = SET_TO igds_level_name = Err_Vertex_mismatch_@Value(fme_feature_type)_@Value(OBJECTID)_OBJ_ID_GDB
    -> Junction_2
Tester_16
    BOOL_OP = OR
    COMPOSITE_TEST = 1
    TEST_CLAUSE = TEST @Value(fme_feature_type) = ServInst_pol
    TEST_MODE = TEST
    PASSED -> VertexExtractor_12
    PASSED -> GeometryCoercer_6
VertexExtractor_12
    Point -> PointOnPointOverlayer_6 [POINT]
PointOnPointOverlayer_6
    DEAGGREGATE_INPUT = Yes
    OV_ATTR = P_overlaps
    TOLERANCE = 0.01
    POINT -> Tester_40
Tester_40
    BOOL_OP = OR
    COMPOSITE_TEST = 1
    TEST_CLAUSE = TEST @Value(PoinT_LINE) = Yes
    TEST_MODE = TEST
    PASSED -> Tester_41
Tester_41
    BOOL_OP = OR
    COMPOSITE_TEST = 1
    TEST_CLAUSE = TEST @Value(P_overlaps) = 0
    TEST_MODE = TEST
    PASSED -> PointOnLineOverlayer_7 [POINT]
GeometryCoercer_6
    GQUERY:
      for $geom in //geometry
      where $geom/count(parent::geometry) = 0
      return number($geom/@fme_id)
    KIND = fme_line
    COERCED -> PointOnLineOverlayer_7 [LINE]
PointOnLineOverlayer_7
    DEAGGREGATE_INPUT = Yes
    MEASURE_TYPE = Continuous
    MERGE_MEASURES = Yes
    OV_ATTR = PP_overlaps
    TOLERANCE = 0.01
    POINT -> Tester_42
Tester_42
    BOOL_OP = OR
    COMPOSITE_TEST = 1
    TEST_CLAUSE = TEST @Value(PP_overlaps) = 0
    TEST_MODE = TEST
    FAILED -> AttributeCreator_18
AttributeCreator_18
    ATTR_TABLE = SET_TO igds_level_name = Err_Vertex_mismatch_@Value(fme_feature_type)_@Value(OBJECTID)_OBJ_ID_GDB
    -> Junction_2

Bookmark: Hydro_NON_FLAT_Elements
Tester_44
    BOOL_OP = OR
    COMPOSITE_TEST = 1
    TEST_CLAUSE = TEST @Value(fme_feature_type) = Hidrografia_pol
    TEST_MODE = TEST
    PASSED -> Tester_43
Tester_43
    BOOL_OP = OR
    COMPOSITE_TEST = 1 OR 2
    TEST_CLAUSE:
      TEST @Value(ID_Fenomen) = 06005
      TEST @Value(ID_Fenomen) = 06007
    TEST_MODE = TEST
    PASSED -> Counter_2
Note: Road_LINE_AXIS_CNX_Errros
Counter_2
    CNT_ATTR = _WID_
    DOMAIN = counter
    SCOPE = Global
    START = 1
    -> VertexExtractor_14
    -> FeatureJoiner [LEFT]
VertexExtractor_14
    Point -> StatisticsCalculator
StatisticsCalculator
    CALCULATION_MODE = NUMERIC
    FEAT_STATS = _WID_,NUMERIC_MODE,MIN,MAX,,,,,,,,,,
    GROUP_BY = _WID_
    SUMMARY -> Tester_45
Tester_45
    BOOL_OP = OR
    COMPOSITE_TEST = 1
    TEST_CLAUSE = TEST @Value(_WID_.max) != @Value(_WID_.min)
    TEST_MODE = TEST
    PASSED -> FeatureJoiner [RIGHT]
FeatureJoiner
    ATTR_CONFLICT_RES = Use Left
    GEOMETRY_HANDLING = Use Left
    JOIN_KEYS = _WID_ _WID_ AUTO
    JOIN_MODE = Inner
    JOINED -> AttributeCreator_19
AttributeCreator_19
    ATTR_TABLE = SET_TO igds_level_name = Err_Hydro_NON_FLAT_@Value(fme_feature_type)_@Value(OBJECTID)_OBJ_ID_GDB
    -> Junction_2

Bookmark: New Bookmark
Tester_62
    BOOL_OP = OR
    COMPOSITE_TEST = 1
    TEST_CLAUSE = TEST @Value(fme_feature_type) = Hidrografia_pol
    TEST_MODE = TEST
    FAILED -> Tester_63
Tester_63
    BOOL_OP = OR
    COMPOSITE_TEST = 1
    TEST_CLAUSE = TEST @Value(fme_feature_type) = Hidrografia_lin
    TEST_MODE = TEST
    PASSED -> Tester_64
Tester_64
    BOOL_OP = OR
    COMPOSITE_TEST = 1
    TEST_CLAUSE = TEST @Value(COMPONEN1D) = CNX
    TEST_MODE = TEST
    PASSED -> LineCombiner
LineCombiner
    ACCUM_ATTRS_NAME = Use Attributes From One Feature
    BREAK = no
    BREAK_CONNECTION_ATTRIBUTES = COMPONEN1D
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> SpatialFilter_3 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    FAILED -> AttributeCreator_28

Bookmark: Road_LINE & POlygon
Tester_48
    BOOL_OP = OR
    COMPOSITE_TEST = 1
    TEST_CLAUSE = TEST @Value(fme_feature_type) = RedViaria_lin
    TEST_MODE = TEST
    PASSED -> Tester_46
    PASSED -> Tester_56
    PASSED -> Tester_58
    PASSED -> Tester_60
Tester_47
    BOOL_OP = OR
    COMPOSITE_TEST = 1
    TEST_CLAUSE = TEST @Value(fme_feature_type) = RedViaria_pol
    TEST_MODE = TEST
    PASSED -> LineOnAreaOverlayer [AREA]
    PASSED -> Tester_57
    PASSED -> SpatialFilter_3 [Filter]

Bookmark: Road_LINE_AXIS_CNX_Errros
Tester_60
    BOOL_OP = OR
    COMPOSITE_TEST = 1 OR 2
    TEST_CLAUSE:
      TEST @Value(CLASIF) = EJE
      TEST @Value(CLASIF) = LIN
    TEST_MODE = TEST
    PASSED -> LineOnLineOverlayer [LINE]
LineOnLineOverlayer
    ATTRS_ACCUM_MODE = Merge Attributes
    CLEANING_TOLERANCE = 0.01
    DEAGGREGATE_INPUT = Yes
    GENERATE_LIST_DROP = NO
    INCOMING_PREFIX = EJE_overlaps
    OV_ATTR = EJE_overlaps
    SEPARATE_COLLINEAR_SEGMENTS = No
    LINE -> Tester_61
    COLLAPSED -> AttributeCreator_25
Tester_61
    BOOL_OP = OR
    COMPOSITE_TEST = 1
    TEST_CLAUSE = TEST @Value(EJE_overlaps) = 1
    TEST_MODE = TEST
    FAILED -> AttributeCreator_25
AttributeCreator_25
    ATTR_TABLE = SET_TO igds_level_name = Err_Road_CNX_Issues_@Value(fme_feature_type)_@Value(OBJECTID)_OBJ_ID_GDB
    -> Junction

Bookmark: Road-Other_Checks
Tester_46
    BOOL_OP = OR
    COMPOSITE_TEST = 1 OR 2 OR 3 OR 4
    TEST_CLAUSE:
      TEST @Value(CLASIF) = CNX
      TEST @Value(CLASIF) = EJE
      TEST @Value(CLASIF) = LIN
      TEST @Value(CLASIF) = BOR
    TEST_MODE = TEST
    PASSED -> Tester_52
Tester_52
    BOOL_OP = OR
    COMPOSITE_TEST = 1
    TEST_CLAUSE = TEST @Value(CLASIF) = CNX
    TEST_MODE = TEST
    PASSED -> LineOnAreaOverlayer [LINE]
    FAILED -> Tester_54
Tester_54
    BOOL_OP = OR
    COMPOSITE_TEST = 1
    TEST_CLAUSE = TEST @Value(CLASIF) = EJE
    TEST_MODE = TEST
    PASSED -> LineOnAreaOverlayer_2 [LINE]
LineOnAreaOverlayer
    ATTR_ACCUM_MODE = Prefix Incoming
    CLEANING_TOLERANCE = 0.01
    DEAGGREGATE_INPUT = Yes
    INCOMING_PREFIX = _CNX_Road_Overlap
    OV_ATTR = _CNX_Road_Overlap
    LINE -> Tester_53
    AREA -> Tester_17
Tester_53
    BOOL_OP = OR
    COMPOSITE_TEST = 1
    TEST_CLAUSE = TEST @Value(_CNX_Road_Overlap) = 1
    TEST_MODE = TEST
    FAILED -> AttributeCreator_22
AttributeCreator_22
    ATTR_TABLE = SET_TO igds_level_name = Err_Road_CNX_@Value(fme_feature_type)_@Value(OBJECTID)_OBJ_ID_GDB
    -> Junction_2
Tester_17
    BOOL_OP = OR
    COMPOSITE_TEST = 1
    TEST_CLAUSE = TEST @Value(TIPO) = PUE
    TEST_MODE = TEST
    FAILED -> LineOnAreaOverlayer_2 [AREA]
LineOnAreaOverlayer_2
    ATTR_ACCUM_MODE = Prefix Incoming
    CLEANING_TOLERANCE = 0.01
    DEAGGREGATE_INPUT = Yes
    INCOMING_PREFIX = _CNX_Road_Overlap
    OV_ATTR = _CNX_Road_Overlap
    LINE -> Tester_55
Tester_55
    BOOL_OP = OR
    COMPOSITE_TEST = 1
    TEST_CLAUSE = TEST @Value(_CNX_Road_Overlap) = 1
    TEST_MODE = TEST
    FAILED -> AttributeCreator_23
AttributeCreator_23
    ATTR_TABLE = SET_TO igds_level_name = Err_Road_EJE_Issues_@Value(fme_feature_type)_@Value(OBJECTID)_OBJ_ID_GDB
    -> Junction

Bookmark: Bridge_ELE_CHECK
Tester_56
    BOOL_OP = OR
    COMPOSITE_TEST = 1
    TEST_CLAUSE = TEST @Value(SITUACION) = 1
    TEST_MODE = TEST
    PASSED -> SpatialFilter_2 [Candidate]
GeometryFilter_2
    BREAK_AGG = No
    GEOM_PORT_NAMES = Line Area
    AREA -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS TOUCHES
    USE_BOUNDING_BOX = No
    FAILED -> AttributeCreator_24
AttributeCreator_24
    ATTR_TABLE = SET_TO igds_level_name = Err_Road_ELE_Bridge_@Value(fme_feature_type)_@Value(OBJECTID)_OBJ_ID_GDB
    -> Junction

Bookmark: Road_VAD_Check
Tester_58
    BOOL_OP = OR
    COMPOSITE_TEST = 1
    TEST_CLAUSE = TEST @Value(SITUACION) = 4
    TEST_MODE = TEST
    PASSED -> SpatialFilter_4 [Filter]
Tester_57
    BOOL_OP = OR
    COMPOSITE_TEST = 1
    TEST_CLAUSE = TEST @Value(SITUACION) = 4
    TEST_MODE = TEST
    PASSED -> SpatialFilter_4 [Candidate]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    FAILED -> AttributeCreator_29
Note: Road_VAD_Check
AttributeCreator_29
    ATTR_TABLE = SET_TO igds_level_name = Err_Road_VAD_@Value(fme_feature_type)_@Value(OBJECTID)_OBJ_ID_GDB
    -> Junction

Bookmark: Bride
Tester_25
    BOOL_OP = OR
    COMPOSITE_TEST = 1
    TEST_CLAUSE = TEST @Value(TIPO) = PUE
    TEST_MODE = TEST
    PASSED -> GeometryFilter_2

Bookmark: Firewall_Multiple_polygons_Check
Tester_71
    BOOL_OP = OR
    COMPOSITE_TEST = 1
    TEST_CLAUSE = TEST @Value(ID_Fenomen) = 12001
    TEST_MODE = TEST
    PASSED -> Dissolver_2
    PASSED -> SpatialFilter_5 [Filter]
Dissolver_2
    ACCUM_INPUT_ATTRS = Use Attributes From One Feature
    CLEANING_TOLERANCE = 0.01
    CONNECT_Z_MODE = First Wins
    DEAGGREGATE_INPUT = Yes
    GROUP_BY = TIPO FIGURA
    REMNANTS -> AttributeCreator_30
AttributeCreator_30
    ATTR_TABLE = SET_TO igds_level_name = Err_Firewall_Multi_POLY_Merge
    -> Junction
