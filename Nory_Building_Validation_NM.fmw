FME workspace Nory_Building_Validation_NM.fmw

Parameters:
- SourceDataset_DGNV8 = C:\FME\BID_4626_Øygarden_230627.dgn   # Source Bentley MicroStation Design File(s)
- FEATURE_TYPES = 501L_BuildingDivide 503L_RoofEdge 505L_Facadedelimitation 506L_FoundationWall 507L_FictitiousBuildingDelimitation 508L_BuildingLine 509L_BuildingLine 510L_3DSupportline 511L_3DSupportline 515L_RoofRidge 516L_RoofRidge 521L_Roofdivide 522L_Roofdivide 523L_RoofdivideBottom 524L_RoofdivideBottom 530L_Veranda 531L_Veranda_Bottom 532L_Veranda 533L_Stairs 535L_CanopyEdge Building_Polygon OtherBuilding Building Building_Point
- DestDataset_DGNV8 = C:\FME\New folder\test.dgn   # Destination Bentley MicroStation Design File
- SourceDataset_DGNV8_2 = C:\FME\construction.dgn   # Source Bentley MicroStation Design File(s)
- FEATURE_TYPES_2 = 50 KystkonturTekniskeAnlegg 536L_WallFreeStanding 542L_BridgeDetail 543L_Culvert 544L_Subdrain 545L_TunnelMouth 555L_StairsFreestandingDelimitation 557L_FoundationDelimitation 560P_Chimney 561L_ChimneyDelimitation 565L_Ruin 567L_TankDelimitation 569L_TowerDelimitation 570L_Fence 571L_Stonewall 572L_SustainingWallDelimitation 573L_BrickWallFreeStanding 574L_BrickWallVertical 575P_Gatepost 576L_Stonewall 576P_Beacon 577L_Shield_Noise 582L_Shield_Shelter 584L_Mound_Noise 585L_Mound_Snow 588L_Mound_Flood_protection 591L_WallFreeStanding 592L_DescriptiveConstructionline 595L_Damdelimitation 601L_RiverSillDelimitation 602L_FictitiousDelimitationConstruction 604L_FishFlakeDelimitation_Bottom 605L_FishFlakeDelimitation_Top 606L_FishFlakeRidge 609L_FloatingStageDelimitation 610L_FloatingStageGangway 613L_QuayDelimitation 615L_JettyDelimitation 616L_FishFarmTub 618L_FishFarmNetCageDelimitation 620L_Pipeline 621L_DryDock 625L_SportsConstruction 627L_ShootingRangeInstallation 630L_PoolDelimitation 633L_StandDelimitation 641L_Bridge_Road 642L_Bridge_WalkCyclePath 645L_Bridge_Unkown 645L_Bridge_WaterAqueduct 646P_ParkDetail_Other 648P_ParkDetail_Bauta 653L_ParkDetail_Bauta 655L_Bridge_Unkown 655L_ParkDetail_Sandpit 10571L_Stonewall 30553P_FlagPole 30570L_Fence 30573L_BrickWallFreeStanding 30577L_Shield_Noise 30592L_DescriptiveConstructionline 40553P_FlagPole 40570L_Fence 40592L_DescriptiveConstructionline 50570L_Fence 50571 50571_L_Stonewall 50571L 50571L_Stonewall 50574L_BrickWallVertical Default FishFarmNetCage
- DestDataset_DGNV8_3 = C:\FME\New folder\test.dgn   # Destination Bentley MicroStation Design File

Readers:
- DGNV8_1: DGNV8 from $(SourceDataset_DGNV8)
- DGNV8_3: DGNV8 from $(SourceDataset_DGNV8_2)

Writers:
- DGNV8_2: DGNV8 to $(DestDataset_DGNV8)
- DGNV8_4: DGNV8 to $(DestDataset_DGNV8_3)

Note: Building
DELETED (reader DGNV8_1)
    -> AttributeFilter
    -> GeometryFilter
GeometryFilter
    FILTER_MODE = SIMPLE
    FILTER_MULTI = FILTER_TYPES]"Point Area Surface"]FME_CONTROLLER_QUERY_FILE]]FME_CONTROLLER_CHOICE]Simple
    Point -> AttributeFilter_4
    Area -> AttributeFilter_3
AttributeFilter_3
    ATTR_NAME = igds_level_name
    ATTR_VALUES = <Empty>,<Missing>,<Null>,<Unfiltered>,Building_Polygon
    Building_Polygon -> SpatialFilter_4 [Candidate]
    Building_Polygon -> AreaCalculator_2
AreaCalculator_2
    AREA_ATTR = _area
    AREA_TYPE = Plane Area
    MULT = 1
    -> Tester_2
Tester_2
    BOOL_OP = OR
    TEST_CLAUSE = TEST @Value(_area) >= 3
    TEST_MODE = TEST
    FAILED -> AttributeCreator_17
AttributeCreator_17
    ATTR_TABLE = SET_TO Error (varchar(200)) = Err_@Value(igds_level_name)_Small area
    -> ERROR (writer DGNV8_2)
AttributeFilter_4
    ATTR_NAME = igds_level_name
    ATTR_VALUES = <Empty>,<Missing>,<Null>,<Unfiltered>,OtherBuilding
    OtherBuilding -> SpatialFilter_4 [Filter]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter_5 [Filter]
AttributeFilter
    ATTR_NAME = igds_level_name
    ATTR_VALUES = <Empty>,<Missing>,<Null>,<Unfiltered>,501L_BuildingDivide,503L_RoofEdge,506L_FoundationWall,507L_FictitiousBuildingDelimitation,508L_BuildingLine,509L_BuildingLine,510L_3DSupportline,511L_3DSupportline,515L_RoofRidge,516L_RoofRidge,521L_Roofdivide,522L_Roofdivide,523L_RoofdivideBottom,524L_RoofdivideBottom,530L_Veranda,531L_Veranda,531L_Veranda_Bottom,532L_Veranda,533L_Stairs,535L_CanopyEdge
    501L_BuildingDivide -> SpatialFilter_5 [Candidate]
    503L_RoofEdge -> 508_Filter [Filter]
    503L_RoofEdge -> 509_Filter [Filter]
    503L_RoofEdge -> 533_Filter [Filter]
    503L_RoofEdge -> 555_Filter [Filter]
    503L_RoofEdge -> SpatialFilter_3 [Filter]
    503L_RoofEdge -> Intersector_4
    503L_RoofEdge -> Junction
    506L_FoundationWall -> 533_Filter [Filter]
    506L_FoundationWall -> 555_Filter [Filter]
    507L_FictitiousBuildingDelimitation -> 533_Filter [Filter]
    507L_FictitiousBuildingDelimitation -> Intersector_2
    508L_BuildingLine -> Extract_End_Points [Input_Features]
    508L_BuildingLine -> SpatialFilter_2 [Filter]
    509L_BuildingLine -> 509_Filter [Candidate]
    509L_BuildingLine -> 515_Filter [Filter]
    509L_BuildingLine -> 516_Filter [Filter]
    509L_BuildingLine -> SpatialFilter [Filter]
    509L_BuildingLine -> 509_Free_End
    509L_BuildingLine -> 508_Filter_3 [Filter]
    509L_BuildingLine -> Intersector_3
    510L_3DSupportline -> SpatialFilter [Candidate]
    510L_3DSupportline -> PointOnLineOverlayer [LINE]
    511L_3DSupportline -> SpatialFilter_3 [Candidate]
    515L_RoofRidge -> 515_Filter [Candidate]
    515L_RoofRidge -> SpatialFilter_2 [Filter]
    515L_RoofRidge -> GeometryValidator_3
    515L_RoofRidge -> Extract_End_Points_2 [Input_Features]
    515L_RoofRidge -> Counter_5
    516L_RoofRidge -> 516_Filter [Candidate]
    516L_RoofRidge -> SpatialFilter_2 [Filter]
    516L_RoofRidge -> GeometryValidator_4
    521L_Roofdivide -> 509_Filter [Filter]
    521L_Roofdivide -> Intersector
    521L_Roofdivide -> SpatialFilter_3 [Filter]
    521L_Roofdivide -> 508_Filter_2 [Filter]
    521L_Roofdivide -> Junction
    522L_Roofdivide -> Intersector
    523L_RoofdivideBottom -> Intersector_2
    524L_RoofdivideBottom -> Intersector_2
    530L_Veranda -> 533_Filter [Filter]
    530L_Veranda -> LineCombiner_6
    530L_Veranda -> 555_Filter [Filter]
    531L_Veranda -> 533_Filter [Filter]
    531L_Veranda -> LineCombiner_5
    531L_Veranda -> 555_Filter [Filter]
    531L_Veranda_Bottom -> 533_Filter [Filter]
    531L_Veranda_Bottom -> LineCombiner_4
    531L_Veranda_Bottom -> 555_Filter [Filter]
    532L_Veranda -> 533_Filter [Filter]
    532L_Veranda -> LineCombiner_3
    532L_Veranda -> 555_Filter [Filter]
    533L_Stairs -> LineCombiner
    535L_CanopyEdge -> 508_Filter [Filter]
    535L_CanopyEdge -> LineCombiner_7
    535L_CanopyEdge -> SpatialFilter_3 [Filter]
    535L_CanopyEdge -> Junction
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_20
AttributeCreator_20
    ATTR_TABLE = SET_TO Error (varchar(200)) = Err_@Value(igds_level_name)_Correct Code
    -> ERROR (writer DGNV8_2)
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN CONTAINS
    USE_BOUNDING_BOX = No
    PASSED -> AttributeCreator_18
AttributeCreator_18
    ATTR_TABLE = SET_TO Error (varchar(200)) = Err_@Value(igds_level_name)_Illlegal_OtherBuildingPT
    -> ERROR (writer DGNV8_2)
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    FAILED -> AttributeCreator_19
AttributeCreator_19
    ATTR_TABLE = SET_TO Error (varchar(200)) = Err_@Value(igds_level_name)_Correct Code
    -> ERROR (writer DGNV8_2)
LineCombiner
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> 533_Filter [Candidate]
533_Filter: SpatialFilter
    AGGREGATE_HANDLING = Yes
    BASE_TYPE = Multiple Filters
    CURVE_BOUNDARY_RULE_PARAM = Default Rule
    PASS_CRITERIA = Pass Against One Filter
    PREDATTR = _predicate
    PREDICATES = INTERSECTS TOUCHES
    USE_BOUNDING_BOX = No
    FAILED -> AttributeCreator_14
AttributeCreator_14
    ATTR_TABLE = SET_TO Error (varchar(200)) = Err_@Value(igds_level_name)_Wrong code
    -> ERROR (writer DGNV8_2)
Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> CenterPointExtractor
CenterPointExtractor
    CENTX = _inside_x
    CENTY = _inside_y
    CENTZ = _inside_z
    EXTRACTIONMODE = CENTEROFGRAV
    -> Clipper [CANDIDATE]
    -> Bufferer_2
Bufferer_2
    ANGLE = 22.5
    CAP_STYLE = Arc
    CORNER_STYLE = Arc
    MODE = AREA
    OFFSET = 0.01
    OFFSET_UNITS = NONE
    PRECISION = APPROX
    BUFFERED -> Clipper_2 [CLIPPER]
Intersector_2
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> CenterPointExtractor_2
    NODE -> 555_Filter [Filter]
CenterPointExtractor_2
    CENTX = _inside_x
    CENTY = _inside_y
    CENTZ = _inside_z
    EXTRACTIONMODE = CENTEROFGRAV
    -> Bufferer
    -> Clipper_2 [CANDIDATE]
Bufferer
    ANGLE = 22.5
    CAP_STYLE = Arc
    CORNER_STYLE = Arc
    MODE = AREA
    OFFSET = 0.01
    OFFSET_UNITS = NONE
    PRECISION = APPROX
    BUFFERED -> Clipper [CLIPPER]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AttributeCreator_16
AttributeCreator_16
    ATTR_TABLE = SET_TO Error (varchar(200)) = Err_@Value(igds_level_name)_523 Missing
    -> ERROR (writer DGNV8_2)
Clipper_2
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AttributeCreator_15
AttributeCreator_15
    ATTR_TABLE = SET_TO Error (varchar(200)) = Err_@Value(igds_level_name)_521 Missing
    -> ERROR (writer DGNV8_2)
LineCombiner_7
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> AreaBuilder_4
    LINE -> 555_Filter [Filter]
AreaBuilder_4
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> AreaCalculator_4
AreaCalculator_4
    AREA_ATTR = _area
    AREA_TYPE = Plane Area
    MULT = 1
    -> Tester_6
Tester_6
    BOOL_OP = OR
    TEST_CLAUSE = TEST @Value(_area) >= 6
    TEST_MODE = TEST
    FAILED -> AttributeCreator_11
AttributeCreator_11
    ATTR_TABLE = SET_TO Error (varchar(200)) = Err_@Value(igds_level_name)_check
    -> ERROR (writer DGNV8_2)
GeometryValidator_3
    ISSUE_ATTR_NAME = _issues
    PRESETS = Custom
    REPAIR = Yes
    RULES = CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS MISSING_VERTEX_NORMALS FME_CONTROLLER_QUERY_FILE]transformers/dependencies/geometryvalidator8/MISSING_VERTEX_NORMALS.fme]FME_CONTROLLER_CHOICE]MISSING_VERTEX_NORMALS SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING
    SUMMARY = Detailed
    PASSED -> BoundsExtractor
BoundsExtractor
    ZMAX = _zmax
    ZMIN = _zmin
    -> Tester_7
Tester_7
    BOOL_OP = OR
    TEST_CLAUSE = TEST @Value(_zmax) != @Value(_zmin)
    TEST_MODE = TEST
    PASSED -> AttributeCreator
AttributeCreator
    ATTR_TABLE = SET_TO Z_Elevation (varchar(200)) = @sub(@Value(_zmax),@Value(_zmin))
    -> Tester_8
Tester_8
    BOOL_OP = OR
    TEST_CLAUSE = TEST @Value(Z_Elevation) >= 0.5
    TEST_MODE = TEST
    PASSED -> AttributeCreator_6
AttributeCreator_6
    ATTR_TABLE = SET_TO Error (varchar(200)) = Err_@Value(igds_level_name)_in Slope
    -> ERROR (writer DGNV8_2)
GeometryValidator_4
    ISSUE_ATTR_NAME = _issues
    PRESETS = Custom
    REPAIR = Yes
    RULES = CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS MISSING_VERTEX_NORMALS FME_CONTROLLER_QUERY_FILE]transformers/dependencies/geometryvalidator8/MISSING_VERTEX_NORMALS.fme]FME_CONTROLLER_CHOICE]MISSING_VERTEX_NORMALS SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING
    SUMMARY = Detailed
    PASSED -> BoundsExtractor_2
BoundsExtractor_2
    ZMAX = _zmax
    ZMIN = _zmin
    -> Tester_4
Tester_4
    BOOL_OP = OR
    TEST_CLAUSE = TEST @Value(_zmax) != @Value(_zmin)
    TEST_MODE = TEST
    PASSED -> AttributeCreator_4
AttributeCreator_4
    ATTR_TABLE = SET_TO Z_Elevation (varchar(200)) = @sub(@Value(_zmax),@Value(_zmin))
    -> Tester_5
Tester_5
    BOOL_OP = OR
    TEST_CLAUSE = TEST @Value(Z_Elevation) >= 0.5
    TEST_MODE = TEST
    PASSED -> AttributeCreator_5
AttributeCreator_5
    ATTR_TABLE = SET_TO Error (varchar(200)) = Err_@Value(igds_level_name)_in Slope
    -> ERROR (writer DGNV8_2)
Junction
    -> SpatialFilter_7 [Candidate]
    -> Tester_14
Tester_14
    BOOL_OP = OR
    TEST_CLAUSE = TEST @Value(igds_level_name) = 503L_RoofEdge
    TEST_MODE = TEST
    PASSED -> SpatialFilter_8 [Filter]
515_Filter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN
    USE_BOUNDING_BOX = No
    PASSED -> ERROR (writer DGNV8_2)
516_Filter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN TOUCHES
    USE_BOUNDING_BOX = No
    FAILED -> ERROR (writer DGNV8_2)
509_Filter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator_8
AttributeCreator_8
    ATTR_TABLE = SET_TO Error (varchar(200)) = Err_@Value(igds_level_name)_wrong code
    -> ERROR (writer DGNV8_2)
Intersector_4
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> CenterPointExtractor_5
CenterPointExtractor_5
    CENTX = _inside_x
    CENTY = _inside_y
    CENTZ = _inside_z
    EXTRACTIONMODE = CENTEROFGRAV
    -> SpatialFilter_6 [Candidate]
Extract_End_Points: Extract End Points
    Buffer = 0
    BufferUnit = Meters
    ExtractGeometry = Yes
    Point_Output -> 508_Filter [Candidate]
508_Filter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    FAILED -> 508_Filter_2 [Candidate]
508_Filter_2: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    FAILED -> 508_Filter_3 [Candidate]
508_Filter_3: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> PointOnLineOverlayer [POINT]
PointOnLineOverlayer
    DEAGGREGATE_INPUT = Yes
    MEASURE_TYPE = Continuous
    MERGE_MEASURES = Yes
    OV_ATTR = _overlaps
    TOLERANCE = 0.02
    POINT -> Tester_9
Tester_9
    BOOL_OP = OR
    TEST_CLAUSE = TEST @Value(_overlaps) = 0
    TEST_MODE = TEST
    PASSED -> AttributeCreator_9
AttributeCreator_9
    ATTR_TABLE = SET_TO Error (varchar(200)) = Err_@Value(igds_level_name)_Missing Supportline
    -> ERROR (writer DGNV8_2)
509_Free_End: Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    Incomplete -> AttributeCreator_7
AttributeCreator_7
    ATTR_TABLE = SET_TO Error (varchar(200)) = Err_@Value(igds_level_name)_Dangle
    -> ERROR (writer DGNV8_2)
Intersector_3
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> CenterPointExtractor_4
CenterPointExtractor_4
    CENTX = _inside_x
    CENTY = _inside_y
    CENTZ = _inside_z
    EXTRACTIONMODE = CENTEROFGRAV
    -> Bufferer_3
Bufferer_3
    ANGLE = 22.5
    CAP_STYLE = Arc
    CORNER_STYLE = Arc
    MODE = AREA
    OFFSET = 0.2
    OFFSET_UNITS = NONE
    PRECISION = APPROX
    BUFFERED -> SpatialFilter_6 [Filter]
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_21
AttributeCreator_21
    ATTR_TABLE = SET_TO Error (varchar(200)) = Err_@Value(igds_level_name)_Connect To Building
    -> Tester_10
Tester_10
    BOOL_OP = OR
    TEST_CLAUSE = TEST @Value(igds_weight) != 0
    TEST_MODE = TEST
    PASSED -> ERROR (writer DGNV8_2)
Extract_End_Points_2: Extract End Points
    Buffer = 0
    BufferUnit = Meters
    ExtractGeometry = Yes
    Point_Output -> Bufferer_4
Bufferer_4
    ANGLE = 22.5
    CAP_STYLE = Round
    CORNER_STYLE = Arc
    MODE = AREA
    OFFSET = 0.02
    OFFSET_UNITS = NONE
    PRECISION = APPROX
    BUFFERED -> SpatialFilter_7 [Filter]
SpatialFilter_7
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeFilter_6
AttributeFilter_6
    ATTR_NAME = igds_level_name
    ATTR_VALUES = <Empty>,<Missing>,<Null>,<Unfiltered>,503L_RoofEdge,523L_RoofdivideBottom,521L_Roofdivide
    521L_Roofdivide -> BoundsExtractor_3
BoundsExtractor_3
    ZMAX = _zmax
    ZMIN = _zmin
    -> Tester_11
    -> Tester_15
Tester_11
    BOOL_OP = OR
    TEST_CLAUSE = TEST @Value(_zmax) != @Value(_zmin)
    TEST_MODE = TEST
    PASSED -> AttributeCreator_10
AttributeCreator_10
    ATTR_TABLE = SET_TO Z_Elevation (varchar(200)) = @sub(@Value(_zmax),@Value(_zmin))
    -> Tester_12
Tester_12
    BOOL_OP = OR
    TEST_CLAUSE = TEST @Value(Z_Elevation) >= 0.5
    TEST_MODE = TEST
    FAILED -> Tester_13
Tester_13
    BOOL_OP = OR
    TEST_CLAUSE = TEST @Value(Z_Elevation) > 0.4
    TEST_MODE = TEST
    PASSED -> Extract_End_Points_4 [Input_Features]
Extract_End_Points_4: Extract End Points
    Buffer = 0
    BufferUnit = Feet
    ExtractGeometry = Yes
    Point_Output -> Bufferer_6
Bufferer_6
    ANGLE = 22.5
    CAP_STYLE = Arc
    CORNER_STYLE = Arc
    MODE = AREA
    OFFSET = 0.1
    OFFSET_UNITS = NONE
    PRECISION = APPROX
    BUFFERED -> Counter_4
Tester_15
    BOOL_OP = OR
    TEST_CLAUSE = TEST @Value(_zmax) = @Value(_zmin)
    TEST_MODE = TEST
    PASSED -> Extract_End_Points_3 [Input_Features]
Extract_End_Points_3: Extract End Points
    Buffer = 0
    BufferUnit = Feet
    ExtractGeometry = Yes
    Point_Output -> Bufferer_5
Bufferer_5
    ANGLE = 22.5
    CAP_STYLE = Arc
    CORNER_STYLE = Arc
    MODE = AREA
    OFFSET = 0.1
    OFFSET_UNITS = NONE
    PRECISION = APPROX
    BUFFERED -> SpatialFilter_8 [Candidate]
SpatialFilter_8
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> Counter_4
Counter_4
    CNT_ATTR = _count
    DOMAIN = counter
    SCOPE = Global
    START = 0
    -> SpatialFilter_9 [Candidate]
Counter_5
    CNT_ATTR = _count
    DOMAIN = counter
    SCOPE = Global
    START = 0
    -> SpatialFilter_9 [Filter]
SpatialFilter_9
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_22
AttributeCreator_22
    ATTR_TABLE = SET_TO Error (varchar(200)) = Err_@Value(igds_level_name)_Check for 508
    -> ERROR (writer DGNV8_2)
LineCombiner_3
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> TopologyBuilder
LineCombiner_4
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> TopologyBuilder
LineCombiner_5
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> TopologyBuilder
LineCombiner_6
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> TopologyBuilder
TopologyBuilder
    ALLOW_CYCLES = No
    BOUNDING_EDGES = All
    CLEANING_TOLERANCE = Automatic
    DEAGGREGATE_INPUT = Yes
    GENERATION_MODE = INTERSECT
    MAX = 0
    OVERLAPPING_MODE = No
    LINE -> AreaBuilder_2
AreaBuilder_2
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Merge Incoming Attributes
    SNAPTYPE_PARAM = None
    AREA -> GeometryValidator
    Incomplete -> AttributeCreator_2
GeometryValidator
    ISSUE_ATTR_NAME = _issues
    PRESETS = Custom
    REPAIR = Yes
    RULES = PLANAR_SURFACE CHECK_AREA]DO_CHECK_AREA]TOLERANCE_MODE]AUTO]TOLERANCE]<Unused>]ANGULAR_TOLERANCE_MODE]IGNORE]ANGULAR_TOLERANCE]<Unused>]FME_CONTROLLER_QUERY_FILE]transformers/dependencies/geometryvalidator8/PLANAR_SURFACE.fme]FME_CONTROLLER_CHOICE]PLANAR_SURFACE
    SUMMARY = Detailed
    PASSED -> GeometryValidator_2
    FAILED -> AttributeCreator_2
    REPAIRED -> Dissolver
Dissolver
    ACCUM_INPUT_ATTRS = Use Attributes From One Feature
    CLEANING_TOLERANCE = Automatic
    CONNECT_Z_MODE = First Wins
    DEAGGREGATE_INPUT = Yes
    AREA -> CenterPointExtractor_3
    AREA -> 3DForcer
CenterPointExtractor_3
    CENTX = _inside_x
    CENTY = _inside_y
    CENTZ = _inside_z
    EXTRACTIONMODE = CENTER
    -> Counter
Counter
    CNT_ATTR = _count
    DOMAIN = counter
    SCOPE = Global
    START = 0
    -> ElevationToMeasureCopier
ElevationToMeasureCopier
    -> 3DForcer
3DForcer
    KEEPZVAL = No
    ZVALATTR = @Value(_inside_z)
    -> GeometryValidator_2
    <REJECTED> -> AttributeCreator_3
GeometryValidator_2
    ISSUE_ATTR_NAME = _issues
    PRESETS = Custom
    REPAIR = Yes
    RULES = PLANAR_SURFACE CHECK_AREA]DO_CHECK_AREA]TOLERANCE_MODE]AUTO]TOLERANCE]<Unused>]ANGULAR_TOLERANCE_MODE]IGNORE]ANGULAR_TOLERANCE]<Unused>]FME_CONTROLLER_QUERY_FILE]transformers/dependencies/geometryvalidator8/PLANAR_SURFACE.fme]FME_CONTROLLER_CHOICE]PLANAR_SURFACE
    SUMMARY = Detailed
    PASSED -> AreaCalculator
AreaCalculator
    AREA_ATTR = _area
    AREA_TYPE = Plane Area
    MULT = 1
    -> Tester
Tester
    BOOL_OP = OR
    TEST_CLAUSE = TEST @Value(_area) >= 6
    TEST_MODE = TEST
    PASSED -> Veranda (writer DGNV8_2)
    FAILED -> ERROR (writer DGNV8_2)
Veranda (writer DGNV8_2)
AttributeCreator_3
    ATTR_TABLE = SET_TO Error_Level (buffer) = Non_Flat
AttributeCreator_2
    ATTR_TABLE = SET_TO Error_Level (buffer) = Non_Flat
    -> ERROR (writer DGNV8_2)
Note: Construction
553P_FlagPole (reader DGNV8_3)
    -> AttributeFilter_2
AttributeFilter_2
    ATTR_NAME = igds_level_name
    ATTR_VALUES = <Empty>,<Missing>,<Null>,<Unfiltered>,555L_StairsFreestandingDelimitation
    555L_StairsFreestandingDelimitation -> LineCombiner_2
LineCombiner_2
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> AreaBuilder_3
AreaBuilder_3
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> 555_Filter [Candidate]
    AREA -> AreaCalculator_3
555_Filter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator_13
AttributeCreator_13
    ATTR_TABLE = SET_TO Error (varchar(200)) = Err_@Value(igds_level_name)_Wrong code
    -> ERROR (writer DGNV8_2)
AreaCalculator_3
    AREA_ATTR = _area
    AREA_TYPE = Plane Area
    MULT = 1
    -> Tester_3
Tester_3
    BOOL_OP = OR
    TEST_CLAUSE = TEST @Value(_area) >= 6
    TEST_MODE = TEST
    FAILED -> AttributeCreator_12
AttributeCreator_12
    ATTR_TABLE = SET_TO Error (varchar(200)) = Err_@Value(igds_level_name)_Small Area
    -> ERROR (writer DGNV8_2)
ERROR (writer DGNV8_2)

FME custom transformer ElevationToMeasureCopier
The FME geometry model supports attaching measures on to features; however the only transformer to do this creates the measures as distances along the feature. In some cases a user may wish to transfer Z values to a measure, and this is what this transformer does. 
This transformer accepts as input any feature that may legitimately have a measure attached; points, lines, areas, text features.
All other geometry types are filtered out and returned via the REJECTED port.

INPUT (input)
    -> GeometryFilter
GeometryFilter
    POINT -> CoordinateConcatenator
    LINE -> CoordinateConcatenator
    ARC -> <REJECTED> (output)
    AREA -> CoordinateConcatenator
    ELLIPSE -> <REJECTED> (output)
    TEXT -> CoordinateConcatenator
    RASTER -> <REJECTED> (output)
    SURFACE -> <REJECTED> (output)
    SOLID -> <REJECTED> (output)
    COLLECTION -> <REJECTED> (output)
    NULL -> <REJECTED> (output)
Note: Extract elevations into csv
CoordinateConcatenator
    COORDINATES_TO_INCLUDE_DIS = Z
    COORD_ATTR = _coordinates
    COORD_DELIM = ,
    -> AttributeSplitter_2
Note: Split csv into list
AttributeSplitter_2
    ATTR_NAME = _coordinates
    DELIMITER = ,
    DROP_EMPTY_PARTS = No
    LIST_NAME = _grid_values
    TRIM_OPTION = Both
    -> GeometryFilter_2
Note: Clean up attributes
AttributeRemover
    LIST_ATTRS = _grid_values{}
    REMOVE_ATTRS = _coordinates
    -> OUTPUT (output)
Note: Output. / Make it high up to appear / uppermost on customer transformer!
OUTPUT (output)
<REJECTED> (output)

Bookmark: Set Measures according to geometry
GeometryFilter_2
    BREAK_AGG = No
    POINT -> Point_MeasureSetter
    LINE -> LineMeasureSetter
    AREA -> Polygone_MeasureSetter
    TEXT -> Text_MeasureSetter
Point_MeasureSetter: MeasureSetter
    GEOM_TYPE = Point
    MEASURE_VAL = @Value(_grid_values{0})
    -> AttributeRemover
LineMeasureSetter
    MEASURE_LIST = _grid_values{}
    -> AttributeRemover
Polygone_MeasureSetter: MeasureSetter
    GEOM_TYPE = Whole Area
    MEASURE_LIST = _grid_values{}
    -> AttributeRemover
Text_MeasureSetter: MeasureSetter
    GEOM_TYPE = All Vertices to Same Value
    MEASURE_VAL = @Value(_grid_values{0})
    -> AttributeRemover

FME custom transformer AngleCalculator
Calculates the angle in degrees for every polygon node.
INPUT:
Polygons
Needed attribute: "OBJECTID"
OUTPUT:
Points with calculated angle between lines 
Attribute: "OBJECTID_pt" (OBJECTID of the associated polygon as attribute)
The angle points can be assigned to their polygon using an object ID.

Parameters:
- OBJECT_ID_LIST = @Value(_list{0}.OBJECTID)   # OBJECTID of the polygon as list attribute
- OBJECTID = @Value(OBJECTID)   # OBJECTID of the polygon

INPUT_Polygons (input)
    -> Junction_15
Note: INPUT: Polygon
Junction_15
    -> Chopper_7
Note: OUTPUT: Angle Points
Junction_16
    -> OUTPUT_Angle_Points (output)
OUTPUT_Angle_Points (output)
Rejected (output)

Bookmark: Angle Calculator
Note: Chop to Line
Chopper_7
    DEAGGREGATE_INPUT = Deaggregate
    MAX_VERTICES = 2
    MODE = By Vertex
    REMNANT_ATTR = _remnant
    CHOPPED -> Intersector_4
    <REJECTED> -> Junction
Note: Nodes of Line Intersection
Intersector_4
    ATTRS_ACCUM_MODE = Use Attributes From One Feature
    CLEANING_TOLERANCE = Automatic
    DEAGGREGATE_INPUT = Yes
    DIRECTION_NAME = _direction
    DUPLICATE_Z_NODES = No
    GENERATE_LIST_DROP = YES
    GRP_BY = OBJECTID
    LIST_ATTRS_TO_INCLUDE = OBJECTID
    LIST_NAME = _list
    MEASURE_TYPE = Continuous
    NODE_NUM_ATTR = _node_number
    OV_ATTR = _overlaps
    SEG_ATTR = _segments
    SEPARATE_COLLINEAR_SEGMENTS = No
    NODE -> ListSorter_3
    <REJECTED> -> Junction
Note: Sort to list_direction to "incoming" first
ListSorter_3
    ORDER = Ascending
    SRC_LIST = _list{}._direction
    TYPE = Alphabetic
    -> AttributeCreator_7
Note: Calculates the angle from the "incoming" and "outgoing" angles.
AttributeCreator_7
    ATTR_TABLE:
      SET_TO angle = FME_CONDITIONAL:DEFAULT_VALUE'@Evaluate(@Value(_list{1}.fme_node_angle)-@Value(_list{0}.fme_node_angle))'BOOL_OP;OR;COMPOSITE_TEST;1;TEST @Evaluate(@Value(_list{1}.fme_node_angle)-@Value(_list{0}.fme_node_angle)) < 0'@Evaluate(360+(@Value(_list{1}.fme_node_angle)-@Value(_list{0}.fme_node_angle)))'FME_NUM_CONDITIONS2___
      SET_TO OBJECTID_pt = @Value(_list{0}.OBJECTID)
    -> Junction_16
Junction
    -> Rejected (output)
