FME workspace Final_Attribute_horn.fmw

Parameters:
- DestDataset_SHAPEFILE =
- DestDataset_SHAPEFILE_4 =
- FEATURE_TYPES =
- FEATURE_TYPES_2 =
- SourceDataset_DGNV8 =
- SourceDataset_SHAPEFILE =

Readers:
- DGNV8_1: DGNV8 from $(SourceDataset_DGNV8)
- SHAPEFILE_1: SHAPEFILE from $(SourceDataset_SHAPEFILE)

Writers:
- SHAPEFILE_2: SHAPEFILE to $(DestDataset_SHAPEFILE)
- SHAPEFILE_3: SHAPEFILE to $(DestDataset_SHAPEFILE_4)

0_Main_Roof (reader DGNV8_1)
    -> GeometryFilter
GeometryFilter
    BREAK_AGG = No
    GEOM_PORT_NAMES = Area
    AREA -> AttributeFilter
    AREA -> CenterPointReplacer_2
    AREA -> PointOnAreaOverlayer_4 [AREA]
AttributeFilter
    ATTR_NAME = fme_feature_type
    ATTR_VALUES = <Empty>,<Missing>,<Null>,<Unfiltered>,0_Main_Roof,1_Outer_Installations,7_Roof_Window
    0_Main_Roof -> Dissolver
Dissolver
    ACCUM_INPUT_ATTRS = Use Attributes From One Feature
    CLEANING_TOLERANCE = 0.1
    CONNECT_Z_MODE = First Wins
    DEAGGREGATE_INPUT = Yes
    AREA -> CenterPointReplacer
    AREA -> PointOnAreaOverlayer_2 [AREA]
CenterPointReplacer
    POINTTYPE = INSIDE
    POINT -> PointOnAreaOverlayer [POINT]
CenterPointReplacer_2
    POINTTYPE = INSIDE
    POINT -> PointOnAreaOverlayer_3 [POINT]
VALENCE_ROMANS_PARCELLES (reader SHAPEFILE_1)
    attributes: fid number(20,0), id varchar(14)
    -> PointOnAreaOverlayer [AREA]
PointOnAreaOverlayer
    ATTR_ACCUM_MODE = Merge Incoming
    ATTR_CONFLICT_RES = Use Original
    DEAGGREGATE_INPUT = Yes
    OV_ATTR = _overlaps
    POLYS_FIRST = NO
    POINT -> AttributeCreator
AttributeCreator
    ATTR_TABLE = SET_TO N_ID = +=1
    -> Counter
Counter
    CNT_ATTR = N_ID
    DOMAIN = counter
    SCOPE = Global
    START = 1
    -> Tester
Tester
    BOOL_OP = OR
    COMPOSITE_TEST = 1
    TEST_CLAUSE = TEST @Value(id) = ""
    TEST_MODE = TEST
    PASSED -> Null_ID (writer SHAPEFILE_2)
    FAILED -> Matcher
Matcher
    BLANK_AND_MISSING_DIFFER = No
    CHECK_TYPES_AND_ENCODINGS = No
    CNT_ATTR = _match_id
    MATCHATTRS = id
    MATCH_STRATEGY = Match Selected Attributes
    MATCHED -> DuplicateFilter_25
    NOT_MATCHED -> GeometryCoercer
GeometryCoercer
    GQUERY:
      for $geom in //geometry
      where $geom/count(parent::geometry) = 0
      return number($geom/@fme_id)
    KIND = fme_point
    COERCED -> PointOnAreaOverlayer_2 [POINT]
PointOnAreaOverlayer_2
    ATTR_ACCUM_MODE = Merge Incoming
    ATTR_CONFLICT_RES = Use Original
    DEAGGREGATE_INPUT = Yes
    OV_ATTR = _overlaps
    POLYS_FIRST = NO
    AREA -> Tester_2
    AREA -> AttributeRemover_3
AttributeRemover_3
    REMOVE_ATTRS = fme_feature_type
    -> PointOnAreaOverlayer_3 [AREA]
PointOnAreaOverlayer_3
    ATTR_ACCUM_MODE = Merge Incoming
    ATTR_CONFLICT_RES = Use Original
    DEAGGREGATE_INPUT = Yes
    OV_ATTR = _overlaps
    POLYS_FIRST = NO
    POINT -> PointOnAreaOverlayer_4 [POINT]
PointOnAreaOverlayer_4
    ATTR_ACCUM_MODE = Merge Incoming
    ATTR_CONFLICT_RES = Use Original
    DEAGGREGATE_INPUT = Yes
    OV_ATTR = _overlaps
    POLYS_FIRST = NO
    AREA -> AttributeRemover_4
AttributeRemover_4
    REMOVE_ATTRS = _overlaps,N_ID
    -> AttributeFilter_2
AttributeFilter_2
    ATTR_NAME = fme_feature_type
    ATTR_VALUES = <Empty>,<Missing>,<Null>,<Unfiltered>,0_Main_Roof,1_Outer_Installations,7_Roof_Window
    0_Main_Roof -> AttributeCreator_28
    1_Outer_Installations -> AttributeCreator_27
    7_Roof_Window -> AttributeCreator_29
AttributeCreator_28
    ATTR_TABLE = SET_TO New_ID = @Value(id)
    -> Shapefile1 (writer SHAPEFILE_3)
AttributeCreator_27
    ATTR_TABLE = SET_TO New_ID = @Value(id)
    -> Shapefile1 (writer SHAPEFILE_3)
AttributeCreator_29
    ATTR_TABLE = SET_TO New_ID = @Value(id)
    -> Shapefile1 (writer SHAPEFILE_3)
Shapefile1 (writer SHAPEFILE_3)
    attributes: igds_level varchar(80), id varchar(20)
Null_ID (writer SHAPEFILE_2)
    attributes: N_ID varchar(200), igds_level varchar(80), fid number(20,0), id varchar(14), _overlaps double

Bookmark: New Bookmark
DuplicateFilter_25
    INPUT_ORDERED_CHOICE = No
    KEYATTR = id
    UNIQUE -> AttributeRemover_2
    DUPLICATE -> AttributeRemover
AttributeRemover_2
    REMOVE_ATTRS = _match_id,_overlaps,fid
    -> AttributeCreator_2
AttributeCreator_2
    ATTR_TABLE = SET_TO id = @Value(id)_1
    -> GeometryCoercer
AttributeRemover
    REMOVE_ATTRS = _match_id,_overlaps,fid
    -> DuplicateFilter
DuplicateFilter
    INPUT_ORDERED_CHOICE = No
    KEYATTR = id
    UNIQUE -> AttributeCreator_3
    DUPLICATE -> DuplicateFilter_2
AttributeCreator_3
    ATTR_TABLE = SET_TO id = @Value(id)_2
    -> GeometryCoercer
DuplicateFilter_2
    INPUT_ORDERED_CHOICE = No
    KEYATTR = id
    UNIQUE -> AttributeCreator_4
    DUPLICATE -> DuplicateFilter_3
AttributeCreator_4
    ATTR_TABLE = SET_TO id = @Value(id)_3
    -> GeometryCoercer
DuplicateFilter_3
    INPUT_ORDERED_CHOICE = No
    KEYATTR = id
    UNIQUE -> AttributeCreator_5
    DUPLICATE -> DuplicateFilter_4
AttributeCreator_5
    ATTR_TABLE = SET_TO id = @Value(id)_4
    -> GeometryCoercer
DuplicateFilter_4
    INPUT_ORDERED_CHOICE = No
    KEYATTR = id
    UNIQUE -> AttributeCreator_6
    DUPLICATE -> DuplicateFilter_5
AttributeCreator_6
    ATTR_TABLE = SET_TO id = @Value(id)_5
    -> GeometryCoercer
DuplicateFilter_5
    INPUT_ORDERED_CHOICE = No
    KEYATTR = id
    UNIQUE -> AttributeCreator_7
    DUPLICATE -> DuplicateFilter_6
AttributeCreator_7
    ATTR_TABLE = SET_TO id = @Value(id)_6
    -> GeometryCoercer
DuplicateFilter_6
    INPUT_ORDERED_CHOICE = No
    KEYATTR = id
    UNIQUE -> AttributeCreator_8
    DUPLICATE -> DuplicateFilter_7
AttributeCreator_8
    ATTR_TABLE = SET_TO id = @Value(id)_7
    -> GeometryCoercer
DuplicateFilter_7
    INPUT_ORDERED_CHOICE = No
    KEYATTR = id
    UNIQUE -> AttributeCreator_9
    DUPLICATE -> DuplicateFilter_8
AttributeCreator_9
    ATTR_TABLE = SET_TO id = @Value(id)_8
    -> GeometryCoercer
DuplicateFilter_8
    INPUT_ORDERED_CHOICE = No
    KEYATTR = id
    UNIQUE -> AttributeCreator_10
    DUPLICATE -> DuplicateFilter_9
AttributeCreator_10
    ATTR_TABLE = SET_TO id = @Value(id)_9
    -> GeometryCoercer
DuplicateFilter_9
    INPUT_ORDERED_CHOICE = No
    KEYATTR = id
    UNIQUE -> AttributeCreator_11
    DUPLICATE -> DuplicateFilter_10
AttributeCreator_11
    ATTR_TABLE = SET_TO id = @Value(id)_10
    -> GeometryCoercer
DuplicateFilter_10
    INPUT_ORDERED_CHOICE = No
    KEYATTR = id
    UNIQUE -> AttributeCreator_12
    DUPLICATE -> DuplicateFilter_11
AttributeCreator_12
    ATTR_TABLE = SET_TO id = @Value(id)_11
    -> GeometryCoercer
DuplicateFilter_11
    INPUT_ORDERED_CHOICE = No
    KEYATTR = id
    UNIQUE -> AttributeCreator_13
    DUPLICATE -> DuplicateFilter_12
AttributeCreator_13
    ATTR_TABLE = SET_TO id = @Value(id)_12
    -> GeometryCoercer
DuplicateFilter_12
    INPUT_ORDERED_CHOICE = No
    KEYATTR = id
    UNIQUE -> AttributeCreator_14
    DUPLICATE -> DuplicateFilter_13
AttributeCreator_14
    ATTR_TABLE = SET_TO id = @Value(id)_13
    -> GeometryCoercer
DuplicateFilter_13
    INPUT_ORDERED_CHOICE = No
    KEYATTR = id
    UNIQUE -> AttributeCreator_15
    DUPLICATE -> DuplicateFilter_14
AttributeCreator_15
    ATTR_TABLE = SET_TO id = @Value(id)_14
    -> GeometryCoercer
DuplicateFilter_14
    INPUT_ORDERED_CHOICE = No
    KEYATTR = id
    UNIQUE -> DuplicateFilter_15
    DUPLICATE -> AttributeCreator_16
AttributeCreator_16
    ATTR_TABLE = SET_TO id = @Value(id)_15
    -> GeometryCoercer
DuplicateFilter_15
    INPUT_ORDERED_CHOICE = No
    KEYATTR = id
    UNIQUE -> AttributeCreator_17
    DUPLICATE -> DuplicateFilter_16
AttributeCreator_17
    ATTR_TABLE = SET_TO id = @Value(id)_16
    -> GeometryCoercer
DuplicateFilter_16
    INPUT_ORDERED_CHOICE = No
    KEYATTR = id
    UNIQUE -> AttributeCreator_18
    DUPLICATE -> DuplicateFilter_17
AttributeCreator_18
    ATTR_TABLE = SET_TO id = @Value(id)_17
    -> GeometryCoercer
DuplicateFilter_17
    INPUT_ORDERED_CHOICE = No
    KEYATTR = id
    UNIQUE -> AttributeCreator_19
    DUPLICATE -> DuplicateFilter_18
AttributeCreator_19
    ATTR_TABLE = SET_TO id = @Value(id)_18
    -> GeometryCoercer
DuplicateFilter_18
    INPUT_ORDERED_CHOICE = No
    KEYATTR = id
    UNIQUE -> AttributeCreator_20
    DUPLICATE -> DuplicateFilter_19
AttributeCreator_20
    ATTR_TABLE = SET_TO id = @Value(id)_19
    -> GeometryCoercer
DuplicateFilter_19
    INPUT_ORDERED_CHOICE = No
    KEYATTR = id
    UNIQUE -> AttributeCreator_21
    DUPLICATE -> DuplicateFilter_20
AttributeCreator_21
    ATTR_TABLE = SET_TO id = @Value(id)_20
    -> GeometryCoercer
DuplicateFilter_20
    INPUT_ORDERED_CHOICE = No
    KEYATTR = id
    UNIQUE -> AttributeCreator_22
    DUPLICATE -> DuplicateFilter_21
AttributeCreator_22
    ATTR_TABLE = SET_TO id = @Value(id)_21
    -> GeometryCoercer
DuplicateFilter_21
    INPUT_ORDERED_CHOICE = No
    KEYATTR = id
    UNIQUE -> AttributeCreator_23
    DUPLICATE -> DuplicateFilter_22
AttributeCreator_23
    ATTR_TABLE = SET_TO id = @Value(id)_22
    -> GeometryCoercer
DuplicateFilter_22
    INPUT_ORDERED_CHOICE = No
    KEYATTR = id
    UNIQUE -> AttributeCreator_24
    DUPLICATE -> DuplicateFilter_23
AttributeCreator_24
    ATTR_TABLE = SET_TO id = @Value(id)_23
    -> GeometryCoercer
DuplicateFilter_23
    INPUT_ORDERED_CHOICE = No
    KEYATTR = id
    UNIQUE -> AttributeCreator_25
    DUPLICATE -> DuplicateFilter_24
AttributeCreator_25
    ATTR_TABLE = SET_TO id = @Value(id)_24
    -> GeometryCoercer
DuplicateFilter_24
    INPUT_ORDERED_CHOICE = No
    KEYATTR = id
    UNIQUE -> AttributeCreator_26
    UNIQUE -> DuplicateFilter_26
AttributeCreator_26
    ATTR_TABLE = SET_TO id = @Value(id)_25
    -> GeometryCoercer

Bookmark: New_Duplicate
DuplicateFilter_26
    INPUT_ORDERED_CHOICE = No
    KEYATTR = id

Bookmark: Null_ID
Tester_2
    BOOL_OP = OR
    COMPOSITE_TEST = 1
    TEST_CLAUSE = TEST @Value(id) = ""
    TEST_MODE = TEST
