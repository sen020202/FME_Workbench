FME workspace geodatabase_file2geodatabase_file-NEW.fmw

Parameters:
- SourceDataset_GEODATABASE_FILE = $(FME_MF_DIR)Sample-file\566-V2.gdb   # File Geodatabase
- DestDataset_GEODATABASE_FILE = $(FME_MF_DIR)Sample-file\566-V2-New.gdb   # File Geodatabase

Readers:
- GEODATABASE_FILE_1: GEODATABASE_FILE from $(SourceDataset_GEODATABASE_FILE)

Writers:
- GEODATABASE_FILE_2: GEODATABASE_FILE to $(DestDataset_GEODATABASE_FILE) in ETRS89.UTM-30N

Bookmark: Reader Feature Types
LimiteAdministrativo_lin (reader GEODATABASE_FILE_1)
    attributes: OBJECTID integer, objectid_2 integer, ID_Fenomen char(5), CODINE1 char(20), CODINE2 char(20), ENCLAVE1 char(20), ENCLAVE2 char(20), ID_LINLIM char(43), MUN1 char(250), MUN2 char(250), TIPO char(5), URL_RESOUR char(250), SHAPE_Length double
    -> LimiteAdministrativo_lin (writer GEODATABASE_FILE_2)
PuntosGeodesicos_pun (reader GEODATABASE_FILE_1)
    attributes: OBJECTID integer, ID_Fenomen char(5), ASTRONOMIC char(8), FECHACALC char(8), GRAVEDAD char(3), H_ORTO float, ID_HOJA char(5), IDCALC char(10), IDENTIFICA char(10), NOMBRE char(254), ORGANISMOC char(250), REDGEODESI char(3), REDNIVELAC char(3), TITULAR char(3)
    -> PuntosGeodesicos_pun (writer GEODATABASE_FILE_2)
Relieve_pun (reader GEODATABASE_FILE_1)
    attributes: OBJECTID integer, ID_Fenomen char(5), ID_HOJA char(5), CONTEXTO char(3), COTA double, TIPO char(3)
    -> Relieve_pun (writer GEODATABASE_FILE_2)
CubiertaTer_pol (reader GEODATABASE_FILE_1)
    attributes: OBJECTID integer, ID_Fenomen char(5), ID_HOJA char(5), NOMBRE char(254), TIPO char(5), FIGURA char(5), CODIGO char(9), SHAPE_Length double, SHAPE_Area double
    -> CubiertaTer_pol (writer GEODATABASE_FILE_2)
Hidrografia_pol (reader GEODATABASE_FILE_1)
    attributes: OBJECTID integer, SITUACION char(5), CUENCA char(10), CLASIF char(5), CANALIZ char(5), ESTADO char(5), ID_HOJA char(5), NOMBRE char(250), NIVEL char(5), TIPO char(5), SUBCUENCA char(250), REGIMEN char(5), ID_Fenomen char(5), SHAPE_Length double, SHAPE_Area double
    -> Hidrografia_pol (writer GEODATABASE_FILE_2)
ServInst_pol (reader GEODATABASE_FILE_1)
    attributes: OBJECTID integer, ID_Fenomen char(5), CODEXPLOT char(50), ESTADO char(5), ID_HOJA char(5), NOMBRE char(250), TIPO char(5), TITULAR char(5), SITUACION char(5), ENERGIA char(5), CORONACION char(20), COTAMAX char(20), SHAPE_Length double, SHAPE_Area double
    -> ServInst_pol (writer GEODATABASE_FILE_2)
ServInst_pun (reader GEODATABASE_FILE_1)
    attributes: OBJECTID integer, ID_Fenomen char(5), ID_HOJA char(5), NOMBRE char(250), TIPO char(3), CODEXPLOT char(50), ESTADO char(3), ENERGIA char(3)
    -> ServInst_pun (writer GEODATABASE_FILE_2)
ServInst_lin (reader GEODATABASE_FILE_1)
    attributes: OBJECTID integer, ID_Fenomen char(254), CODEXPLOT char(50), ESTADO char(5), ID_HOJA char(5), NOMBRE char(254), TIPO char(5), TITULAR char(254), SITUACION char(5), CLASIF char(5), CORONACION char(20), COTAMAX char(20), SHAPE_Length double
    -> ServInst_lin (writer GEODATABASE_FILE_2)
Hidrografia_pun (reader GEODATABASE_FILE_1)
    attributes: OBJECTID integer, ID_Fenomen char(254), ID_HOJA char(5), NOMBRE char(250), TIPO char(3)
    -> Hidrografia_pun (writer GEODATABASE_FILE_2)
Hidrografia_lin (reader GEODATABASE_FILE_1)
    attributes: OBJECTID integer, SITUACION char(5), CUENCA char(10), CLASIF char(5), CANALIZ char(5), ESTADO char(5), COMPONEN1D char(5), SUBCUENCA char(250), ID_HOJA char(5), NOMBRE char(250), NIVEL char(5), ID_Fenomen char(5), REGIMEN char(5), TIPO char(5), SHAPE_Length double
    -> Hidrografia_lin (writer GEODATABASE_FILE_2)
CubiertaTer_lin (reader GEODATABASE_FILE_1)
    attributes: OBJECTID integer, ID_Fenomen char(5), ID_HOJA char(5), NOMBRE char(250), TIPO char(5), SHAPE_Length double
    -> CubiertaTer_lin (writer GEODATABASE_FILE_2)
Cuadricula_5k_pol (reader GEODATABASE_FILE_1)
    attributes: OBJECTID integer, ID_Fenomen char(5), CF_50K char(5), CF_5K char(5), HUSO char(20), ID_HOJA char(5), NOMBRE char(250), SHAPE_Length double, SHAPE_Area double
    -> Cuadricula_5k_pol (writer GEODATABASE_FILE_2)
EdiPobCons_pun (reader GEODATABASE_FILE_1)
    attributes: OBJECTID integer, ID_Fenomen char(5), ID_HOJA char(5), NOMBRE char(250), TIPO char(3), VISTO char(3), BIC char(3), CLASIF char(3), ESTADO char(3), SITUACION char(3), USO char(3)
    -> EdiPobCons_pun (writer GEODATABASE_FILE_2)
EdiPobCons_lin (reader GEODATABASE_FILE_1)
    attributes: OBJECTID integer, ID_Fenomen char(5), ID_HOJA char(5), TIPO char(5), ESTADO char(5), BIC char(5), CLASIF char(5), SITUACION char(5), USO char(5), NOMBRE char(250), SHAPE_Length double
    -> EdiPobCons_lin (writer GEODATABASE_FILE_2)
RedViaria_pun (reader GEODATABASE_FILE_1)
    attributes: OBJECTID integer, ID_Fenomen char(5), EXTENSION char(20), FECHA_ALTA char(8), FUENTE char(40), ID_VIARIA char(20), ID_PORPK char(20), ID_TRAMO char(20), ID_VIAL char(20), NUMERO double, SENTIDO_PK char(3), TIPO_PORPK char(3)
    -> RedViaria_pun (writer GEODATABASE_FILE_2)
EdiPobCons_pol (reader GEODATABASE_FILE_1)
    attributes: OBJECTID integer, ID_Fenomen char(5), ESTADO char(5), ID_HOJA char(5), TIPO char(5), BIC char(5), CLASIF char(5), NOMBRE char(250), SITUACION char(5), USO char(5), C_NUCLEO_I char(14), D_NUCLEO_I char(80), SHAPE_Length double, SHAPE_Area double
    -> EdiPobCons_pol (writer GEODATABASE_FILE_2)
RedViaria_pol (reader GEODATABASE_FILE_1)
    attributes: OBJECTID integer, ID_Fenomen char(5), ID_HOJA char(5), SITUACION char(5), ESTADOFIS char(5), TITULAR char(5), TIPO_TRAMO char(5), ORDEN char(5), NOMBRE char(250), NOMBRE_ALT char(250), ESTADO char(5), TIPO char(5), VIA char(5), SHAPE_Length double, SHAPE_Area double
    -> RedViaria_pol (writer GEODATABASE_FILE_2)
Relieve_lin (reader GEODATABASE_FILE_1)
    attributes: OBJECTID integer, SONDA char(20), ID_HOJA char(5), SECCION char(5), TIPO char(5), COTA char(20), COMPONEN1D char(5), ID_Fenomen char(5), CLASIF char(5), ORIGEN char(20), PROCEDENCIA char(5), SHAPE_Length double
    -> Relieve_lin (writer GEODATABASE_FILE_2)
RedViaria_lin (reader GEODATABASE_FILE_1)
    attributes: OBJECTID integer, TITULAR char(5), NOMBRE char(250), FIRME char(5), LOCALIDAD char(80), TIPO_TRAMO char(5), FUENTE_V char(5), NOMBRE_CAT char(250), TIPO_VIAL char(5), DGC_VIA char(19), SITUACION char(5), FECHA_ALTA char(8), ID_VIAL char(15), ORDEN char(5), ID_Fenomen char(5), CLASE char(5), SENTIDO char(5), TIPO_VEHIC char(20), VELOCIDAD char(5), TIPO char(5), ESTADOFIS char(5), FECHA_BAJA char(8), ESTADO char(5), CODIGO char(15), ORIGEN_Z char(5), NCARRILES char(5), VIA char(5), CLASIF char(5), CALZADA char(5), ACCESO char(5),
      NOMBRE_ALT char(250), ID_TRAMO char(15), ANCHOCS char(5), ID_HOJA char(5), ITINERANCIA char(20), SHAPE_Length double
    -> RedViaria_lin (writer GEODATABASE_FILE_2)
PuntosGNSS_pun (reader GEODATABASE_FILE_1)
    attributes: OBJECTID integer, ID_Fenomen char(5), COD_IERS char(9), ID_HOJA char(5), IDENTIFICA char(10), RDIS char(250), RED_EPN char(3), RTK char(3), TITULAR char(3)
    -> PuntosGNSS_pun (writer GEODATABASE_FILE_2)
RedFerro_lin (reader GEODATABASE_FILE_1)
    attributes: OBJECTID integer, ID_Fenomen char(5), COMPONEN1D char(3), ANCHO_TIPO char(3), COMPETENCIA char(3), ELECTRIF char(3), ESTADO char(3), ID_HOJA char(5), ID_TRAMO char(15), NOMBRE char(250), NUMVIAS char(3), SITUACION char(3), TITULAR char(3), VELOCIDAD char(3), CODIGOF char(15), ID_TABLERO char(15), SHAPE_Length double
    -> RedFerro_lin (writer GEODATABASE_FILE_2)
RedFerro_pol (reader GEODATABASE_FILE_1)
    attributes: OBJECTID integer, ID_Fenomen char(5), ID_HOJA char(5), CODIGOF char(250), ID_TABLERO char(15), SHAPE_Length double, SHAPE_Area double
    -> RedFerro_pol (writer GEODATABASE_FILE_2)

Bookmark: Writer Feature Types
LimiteAdministrativo_lin (writer GEODATABASE_FILE_2)
    attributes: OBJECTID integer, objectid_2 integer, ID_Fenomen char(5), CODINE1 char(20), CODINE2 char(20), ENCLAVE1 char(20), ENCLAVE2 char(20), ID_LINLIM char(43), MUN1 char(250), MUN2 char(250), TIPO char(5), URL_RESOUR char(250), SHAPE_Length double
PuntosGeodesicos_pun (writer GEODATABASE_FILE_2)
    attributes: OBJECTID integer, ID_Fenomen char(5), ASTRONOMIC char(8), FECHACALC char(8), GRAVEDAD char(3), H_ORTO float, ID_HOJA char(5), IDCALC char(10), IDENTIFICA char(10), NOMBRE char(254), ORGANISMOC char(250), REDGEODESI char(3), REDNIVELAC char(3), TITULAR char(3)
Relieve_pun (writer GEODATABASE_FILE_2)
    attributes: OBJECTID integer, ID_Fenomen char(5), ID_HOJA char(5), CONTEXTO char(3), COTA double, TIPO char(3)
CubiertaTer_pol (writer GEODATABASE_FILE_2)
    attributes: OBJECTID integer, ID_Fenomen char(5), ID_HOJA char(5), NOMBRE char(254), TIPO char(5), FIGURA char(5), CODIGO char(9), SHAPE_Length double, SHAPE_Area double
Hidrografia_pol (writer GEODATABASE_FILE_2)
    attributes: OBJECTID integer, SITUACION char(5), CUENCA char(10), CLASIF char(5), CANALIZ char(5), ESTADO char(5), ID_HOJA char(5), NOMBRE char(250), NIVEL char(5), TIPO char(5), SUBCUENCA char(250), REGIMEN char(5), ID_Fenomen char(5), SHAPE_Length double, SHAPE_Area double
ServInst_pol (writer GEODATABASE_FILE_2)
    attributes: OBJECTID integer, ID_Fenomen char(5), CODEXPLOT char(50), ESTADO char(5), ID_HOJA char(5), NOMBRE char(250), TIPO char(5), TITULAR char(5), SITUACION char(5), ENERGIA char(5), CORONACION char(20), COTAMAX char(20), SHAPE_Length double, SHAPE_Area double
ServInst_pun (writer GEODATABASE_FILE_2)
    attributes: OBJECTID integer, ID_Fenomen char(5), ID_HOJA char(5), NOMBRE char(250), TIPO char(3), CODEXPLOT char(50), ESTADO char(3), ENERGIA char(3)
ServInst_lin (writer GEODATABASE_FILE_2)
    attributes: OBJECTID integer, ID_Fenomen char(254), CODEXPLOT char(50), ESTADO char(5), ID_HOJA char(5), NOMBRE char(254), TIPO char(5), TITULAR char(254), SITUACION char(5), CLASIF char(5), CORONACION char(20), COTAMAX char(20), SHAPE_Length double
Hidrografia_pun (writer GEODATABASE_FILE_2)
    attributes: OBJECTID integer, ID_Fenomen char(254), ID_HOJA char(5), NOMBRE char(250), TIPO char(3)
Hidrografia_lin (writer GEODATABASE_FILE_2)
    attributes: OBJECTID integer, SITUACION char(5), CUENCA char(10), CLASIF char(5), CANALIZ char(5), ESTADO char(5), COMPONEN1D char(5), SUBCUENCA char(250), ID_HOJA char(5), NOMBRE char(250), NIVEL char(5), ID_Fenomen char(5), REGIMEN char(5), TIPO char(5), SHAPE_Length double
CubiertaTer_lin (writer GEODATABASE_FILE_2)
    attributes: OBJECTID integer, ID_Fenomen char(5), ID_HOJA char(5), NOMBRE char(250), TIPO char(5), SHAPE_Length double
Cuadricula_5k_pol (writer GEODATABASE_FILE_2)
    attributes: OBJECTID integer, ID_Fenomen char(5), CF_50K char(5), CF_5K char(5), HUSO char(20), ID_HOJA char(5), NOMBRE char(250), SHAPE_Length double, SHAPE_Area double
EdiPobCons_pun (writer GEODATABASE_FILE_2)
    attributes: OBJECTID integer, ID_Fenomen char(5), ID_HOJA char(5), NOMBRE char(250), TIPO char(3), VISTO char(3), BIC char(3), CLASIF char(3), ESTADO char(3), SITUACION char(3), USO char(3)
EdiPobCons_lin (writer GEODATABASE_FILE_2)
    attributes: OBJECTID integer, ID_Fenomen char(5), ID_HOJA char(5), TIPO char(5), ESTADO char(5), BIC char(5), CLASIF char(5), SITUACION char(5), USO char(5), NOMBRE char(250), SHAPE_Length double
RedViaria_pun (writer GEODATABASE_FILE_2)
    attributes: OBJECTID integer, ID_Fenomen char(5), EXTENSION char(20), FECHA_ALTA char(8), FUENTE char(40), ID_VIARIA char(20), ID_PORPK char(20), ID_TRAMO char(20), ID_VIAL char(20), NUMERO double, SENTIDO_PK char(3), TIPO_PORPK char(3)
EdiPobCons_pol (writer GEODATABASE_FILE_2)
    attributes: OBJECTID integer, ID_Fenomen char(5), ESTADO char(5), ID_HOJA char(5), TIPO char(5), BIC char(5), CLASIF char(5), NOMBRE char(250), SITUACION char(5), USO char(5), C_NUCLEO_I char(14), D_NUCLEO_I char(80), SHAPE_Length double, SHAPE_Area double
RedViaria_pol (writer GEODATABASE_FILE_2)
    attributes: OBJECTID integer, ID_Fenomen char(5), ID_HOJA char(5), SITUACION char(5), ESTADOFIS char(5), TITULAR char(5), TIPO_TRAMO char(5), ORDEN char(5), NOMBRE char(250), NOMBRE_ALT char(250), ESTADO char(5), TIPO char(5), VIA char(5), SHAPE_Length double, SHAPE_Area double
Relieve_lin (writer GEODATABASE_FILE_2)
    attributes: OBJECTID integer, SONDA char(20), ID_HOJA char(5), SECCION char(5), TIPO char(5), COTA char(20), COMPONEN1D char(5), ID_Fenomen char(5), CLASIF char(5), ORIGEN char(20), PROCEDENCIA char(5), SHAPE_Length double
RedViaria_lin (writer GEODATABASE_FILE_2)
    attributes: OBJECTID integer, TITULAR char(5), NOMBRE char(250), FIRME char(5), LOCALIDAD char(80), TIPO_TRAMO char(5), FUENTE_V char(5), NOMBRE_CAT char(250), TIPO_VIAL char(5), DGC_VIA char(19), SITUACION char(5), FECHA_ALTA char(8), ID_VIAL char(15), ORDEN char(5), ID_Fenomen char(5), CLASE char(5), SENTIDO char(5), TIPO_VEHIC char(20), VELOCIDAD char(5), TIPO char(5), ESTADOFIS char(5), FECHA_BAJA char(8), ESTADO char(5), CODIGO char(15), ORIGEN_Z char(5), NCARRILES char(5), VIA char(5), CLASIF char(5), CALZADA char(5), ACCESO char(5),
      NOMBRE_ALT char(250), ID_TRAMO char(15), ANCHOCS char(5), ID_HOJA char(5), ITINERANCIA char(20), SHAPE_Length double
PuntosGNSS_pun (writer GEODATABASE_FILE_2)
    attributes: OBJECTID integer, ID_Fenomen char(5), COD_IERS char(9), ID_HOJA char(5), IDENTIFICA char(10), RDIS char(250), RED_EPN char(3), RTK char(3), TITULAR char(3)
RedFerro_lin (writer GEODATABASE_FILE_2)
    attributes: OBJECTID integer, ID_Fenomen char(5), COMPONEN1D char(3), ANCHO_TIPO char(3), COMPETENCIA char(3), ELECTRIF char(3), ESTADO char(3), ID_HOJA char(5), ID_TRAMO char(15), NOMBRE char(250), NUMVIAS char(3), SITUACION char(3), TITULAR char(3), VELOCIDAD char(3), CODIGOF char(15), ID_TABLERO char(15), SHAPE_Length double
RedFerro_pol (writer GEODATABASE_FILE_2)
    attributes: OBJECTID integer, ID_Fenomen char(5), ID_HOJA char(5), CODIGOF char(250), ID_TABLERO char(15), SHAPE_Length double, SHAPE_Area double
