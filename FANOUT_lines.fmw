FME workspace FANOUT_lines.fmw

Parameters:
- SourceDataset_SHAPEFILE = D:\02_Pilot\Vienna subway\ClientFeedback\Feedback delviery\UG\Vienna_linear.shp   # Source Esri Shapefile(s)
- FEATURE_TYPES = Vienna_linear
- DestDataset_SHAPEFILE = D:\02_Pilot\Vienna subway\ClientFeedback\Feedback delviery\UG\Fanout   # Destination Esri Shapefile Folder

Readers:
- SHAPEFILE_1: SHAPEFILE from $(SourceDataset_SHAPEFILE)

Writers:
- SHAPEFILE_2: SHAPEFILE to $(DestDataset_SHAPEFILE) in EPSG:31256

Vienna_linear (reader SHAPEFILE_1)
    attributes: THEMATIK varchar(200), BETREIBER varchar(254), MATERIAL varchar(200), ANZAHL number(11,0), PROFTYP varchar(200), DIM_L double, DIM_H double, DIM_BEZ varchar(200), L_QUAL long, HOEHE1 number(50,2), H_QUAL1 long, H_BEZ1 varchar(200), HOEHE2 number(50,2), H_QUAL2 long, H_BEZ2 varchar(200), ANGLE long, DETAILS varchar(200), RTRTYP long, length number(50,2)
    -> Vienna_linear (writer SHAPEFILE_2)
Vienna_linear (writer SHAPEFILE_2)
    attributes: THEMATIK varchar(200), BETREIBER varchar(254), MATERIAL varchar(200), ANZAHL number(11,0), PROFTYP varchar(200), DIM_L double, DIM_H double, DIM_BEZ varchar(200), L_QUAL long, HOEHE1 number(50,2), H_QUAL1 long, H_BEZ1 varchar(200), HOEHE2 number(50,2), H_QUAL2 long, H_BEZ2 varchar(200), ANGLE long, DETAILS varchar(200), RTRTYP long, length number(50,2)
