FME workspace Attribute_Extractor.fmw

Parameters:
- DestDataset_ESRISHAPE = $(FME_MF_DIR)DTM\Out\New folder   # Destination Esri Shapefile Folder
- SourceDataset_ESRISHAPE = $(FME_MF_DIR)DTM\DTM_10km_1300_-1000.shp   # Source Esri Shapefile(s)

Readers:
- ESRISHAPE_1: ESRISHAPE from $(SourceDataset_ESRISHAPE) in EPSG:32636

Writers:
- ESRISHAPE_2: ESRISHAPE to $(DestDataset_ESRISHAPE) in EPSG:32636

10km_1600_1000_Spots (reader ESRISHAPE_1)
    attributes: Id long, Layer char(16), ELEVATION float
    -> Counter
Counter
    CNT_ATTR = ID1
    DOMAIN = @Value(fme_basename)
    SCOPE = Local
    START = 1
    -> CoordinateExtractor
CoordinateExtractor
    IND = 0
    MODE = Specify Coordinate
    X_ATTR = _x
    Y_ATTR = _y
    -> 10km_1600_0000_Spots (writer ESRISHAPE_2)
10km_1600_0000_Spots (writer ESRISHAPE_2)
    attributes: Id long, X double, Y double, Z double
