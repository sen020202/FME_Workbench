FME workspace Vector_TopologyChecks_V1.fmw

Parameters:
- PARAMETER_3 =   # Input Block
- SourceDataset_DGNV8 = $(FME_MF_DIR)Sampleexportmach9_hl0015 - comp.dgn   # Source Bentley MicroStation Design File(s)
- FEATURE_TYPES = BackOfSidewalk BROKEN_WHITE BROKEN_YELLOW CURB_BACK CURB_BOTTOM CURB_FRONT CURB_TOP DOTTED_WHITE EOP FrontOfSidewalk SOLID_WHITE SOLID_YELLOW polygon water
- SourceDataset_XLSXR = $(FME_MF_DIR)Book1.xlsx   # Source Microsoft Excel File(s)
- FEATURE_TYPES_3 = Sheet1
- PARAMETER =   # Select Checks
- Val = NO   # SnapCheck_Intersection_Dangle_Overlap_Spike
- Geo = NO   # GeometryType Check
- Pair_elem = NO   # Paired Elements Comparison
- Ver_Gap = NO   # Vertex Interval Check
- all = YES   # All
- PARAMETER_2 =   # Tolerance Block
- xy_Tol = 0.15   # XY Tolerance
- z_Tol = 0.001   # Z Tolerance
- vertex_Tol = 8   # Vertex Interval Value
- pair_Tol = 0.5   # Tolerance For Paired Features
- DestDataset_DGNV8 = $(FME_MF_DIR)_Err_3dsnapcheck2_.dgn   # Destination Bentley MicroStation Design File

Readers:
- DGNV8_1: DGNV8 from $(SourceDataset_DGNV8)
- XLSXR_1: XLSXR from $(SourceDataset_XLSXR)

Writers:
- DGNV8_2: DGNV8 to $(DestDataset_DGNV8)

BROKEN_WHITE (reader DGNV8_1)
    -> FeatureMerger [REQUESTOR]
    -> AttributeFilter
    -> GeometryFilter
    -> TestFilter_42
    -> TestFilter_43
    -> Intersector_3
GeometryFilter
    FILTER_MODE = SIMPLE
    FILTER_MULTI = FILTER_TYPES]"Point Text Line Area"]FME_CONTROLLER_QUERY_FILE]]FME_CONTROLLER_CHOICE]Simple
    Point -> FeatureJoiner_2 [LEFT]
    Text -> FeatureJoiner_2 [LEFT]
    Curve -> FeatureJoiner_2 [LEFT]
    Area -> FeatureJoiner_2 [LEFT]
TestFilter_11
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_4
    @Value(valence) > 2 -> Junction_3
Junction
    -> AttributeCreator_2
Sheet1 (reader XLSXR_1)
    attributes: DGN LEVEL char(15), Geometry char(10), 2DSnap string, 3DSnap number(1,0), Intersection number(1,0), SelfIntersection number(1,0), Dangle number(1,0), Undershoot number(1,0), OverlapFeatures number(1,0), OverlapSegment number(1,0), MissingVertexAtintersection number(1,0), DuplicateVertex number(1,0), PairedFeatures number(1,0), SliverSpike number(1,0), VertexInterval number(1,0), ConstantHeight number(1,0), PolygonDirection char(5), ShortLines number(1,0)
    -> FeatureJoiner_2 [RIGHT]
    -> FeatureMerger [SUPPLIER]
FeatureJoiner_2
    ATTR_CONFLICT_RES = Prefer Left
    GEOMETRY_HANDLING = Prefer Left
    JOIN_KEYS = igds_type Geometry AUTO
    JOIN_MODE = Inner
    UNJOINED_LEFT -> AttributeCreator_21
    UNJOINED_RIGHT -> AttributeCreator_21
Note: DGN geometry type NOT match with XLS
AttributeCreator_21
    ATTR_TABLE = SET_TO igds_level_name (varchar(80)) = __Err_Check_LayerNotDefined_IN_Template_@Value(igds_level_name)
    -> Junction_11
FeatureMerger
    ATTR_ACCUM_MODE = Merge Supplier
    ATTR_CONFLICT_RES = Use Requestor
    GEOM_TYPE = Build Aggregates
    IGNORE_NULLS = No
    JOIN_KEYS = @Value(igds_level_name) @Value(DGN LEVEL) AUTO
    MERGE_TYPE = Attributes Only
    PROCESS_DUPS = YES
    REJECT_NULL_MISSING_KEYS = No
    SUPPLIERS_FIRST = No
    MERGED -> TestFilter_21
    UNMERGED_REQUESTOR -> AttributeCreator_18
    <REJECTED> -> AttributeCreator_18
TestFilter_21
    DEFAULT_VALUE = <UNFILTERED>
    PASSED_TEST_GROUP_OUTPUT = FIRST
    TEST_LIST = "BOOL_OP,OR,COMPOSITE_TEST,""""""1"""""",TEST_CLAUSE,TEST $(Val) = YES",__user_Choice_ = validation,"BOOL_OP,OR,COMPOSITE_TEST,""""""1"""""",TEST_CLAUSE,TEST $(Geo) = YES",__user_Choice_ = GEOMETRY CHECK,"BOOL_OP,OR,COMPOSITE_TEST,""""""1"""""",TEST_CLAUSE,TEST $(Ver_Gap) = YES",__user_Choice_ = VertexGap,"BOOL_OP,OR,COMPOSITE_TEST,""""""1"""""",TEST_CLAUSE,TEST $(Pair_elem) = YES",__user_Choice_ = PAIRED ELEMENT CHECK,"BOOL_OP,OR,COMPOSITE_TEST,""""""1"""""",TEST_CLAUSE,TEST $(all) = YES",__all_ = YES
    __user_Choice_ = validation -> Junction_9
    __user_Choice_ = validation -> Junction_10
    __user_Choice_ = GEOMETRY CHECK -> TestFilter_33
    __user_Choice_ = VertexGap -> TestFilter_25
    __user_Choice_ = PAIRED ELEMENT CHECK -> Junction_8
    __all_ = YES -> Junction_8
    __all_ = YES -> Junction_9
    __all_ = YES -> Junction_10
    __all_ = YES -> TestFilter_33
    __all_ = YES -> TestFilter_25
TestFilter_25
    DEFAULT_VALUE = <UNFILTERED>
    PASSED_TEST_GROUP_OUTPUT = FIRST
    TEST_LIST:
      "BOOL_OP,COMPOSITE,COMPOSITE_TEST,""""""1 AND( 2 OR 3 )"""""",TEST_CLAUSE,TEST VertexInterval ATTRIBUTE_HAS_A_VALUE ""
      TEST $(all) = YES
      TEST $(Ver_Gap) = YES",Vertex Gap
    Vertex Gap -> Chopper_5
Junction_10
    -> TestFilter_28
    -> Counter
    -> Chopper_9
    -> SpikeRemover
    -> GeometryCoercer
TestFilter_28
    DEFAULT_VALUE = <UNFILTERED>
    PASSED_TEST_GROUP_OUTPUT = FIRST
    TEST_LIST:
      "BOOL_OP,COMPOSITE,COMPOSITE_TEST,""""""1 AND( 2 OR 3 )"""""",TEST_CLAUSE,TEST SliverSpike ATTRIBUTE_HAS_A_VALUE ""
      TEST $(all) = YES
      TEST $(Val) = YES",3DSnap ATTRIBUTE_HAS_A_VALUE
    3DSnap ATTRIBUTE_HAS_A_VALUE -> Chopper_8
Junction_8
    -> AttributeExposer
Junction_7
    -> AttributeRemover_2
AttributeRemover_2
    REMOVE_ATTRS = 2DSnap,3DSnap,ConstantHeight,DGN LEVEL,Dangle,DuplicateVertex,Intersection,MissingVertexAtintersection,OverlapFeatures,OverlapSegment,PairedFeatures,PolygonDirection,SelfIntersection,ShortLines,SliverSpike,Undershoot,VertexInterval
    -> AttributeRemover_3
Junction_9
    -> TestFilter_23
    -> TestFilter_22
    -> TestFilter_27
    -> GeometryValidator_2
    -> Chopper_11
    -> TestFilter_30
    -> Chopper_13
    -> CoordinateExtractor_7
    -> TestFilter_38
    -> NodeValence_14 [Line]
    -> TestFilter_44
TestFilter_27
    DEFAULT_VALUE = <UNFILTERED>
    PASSED_TEST_GROUP_OUTPUT = FIRST
    TEST_LIST:
      "BOOL_OP,COMPOSITE,COMPOSITE_TEST,""""""1 AND( 2 OR 3 )"""""",TEST_CLAUSE,TEST SelfIntersection ATTRIBUTE_HAS_A_VALUE ""
      TEST $(all) = YES
      TEST $(Val) = YES",3DSnap ATTRIBUTE_HAS_A_VALUE
    3DSnap ATTRIBUTE_HAS_A_VALUE -> GeometryValidator
Junction_5
    -> AttributeCreator
Snipper_6
    DEAGGREGATE_INPUT = YES
    ENDLOCATIONATTR = 95
    MEASUREMENTTYPE = 2D
    SNIPMODE = Distance (Value)
    STARTLOCATIONATTR = 5
    -> PointOnLineOverlayer [LINE]
PointOnLineOverlayer
    DEAGGREGATE_INPUT = Yes
    MEASURE_TYPE = Continuous
    MERGE_MEASURES = Yes
    OV_ATTR = _overlaps
    TOLERANCE = $(xy_Tol)
    POINT -> PointOnPointOverlayer_2 [POINT]
TestFilter_23
    DEFAULT_VALUE = <UNFILTERED>
    PASSED_TEST_GROUP_OUTPUT = FIRST
    TEST_LIST:
      "BOOL_OP,COMPOSITE,COMPOSITE_TEST,""""""1 AND( 2 OR 3 )"""""",TEST_CLAUSE,TEST 2DSnap ATTRIBUTE_HAS_A_VALUE ""
      TEST $(all) = YES
      TEST $(Val) = YES",2DSnap
    2DSnap -> Counter_2
    2DSnap -> CoordinateExtractor_10
    2DSnap -> CoordinateExtractor_6
    <UNFILTERED> -> Chopper_14
TestFilter_22
    DEFAULT_VALUE = <UNFILTERED>
    PASSED_TEST_GROUP_OUTPUT = FIRST
    TEST_LIST:
      "BOOL_OP,COMPOSITE,COMPOSITE_TEST,""""""1 AND( 2 OR 3 )"""""",TEST_CLAUSE,TEST 3DSnap ATTRIBUTE_HAS_A_VALUE ""
      TEST $(all) = YES
      TEST $(Val) = YES",3DSnap ATTRIBUTE_HAS_A_VALUE
    3DSnap ATTRIBUTE_HAS_A_VALUE -> CoordinateExtractor_11
    3DSnap ATTRIBUTE_HAS_A_VALUE -> CoordinateExtractor_12
    3DSnap ATTRIBUTE_HAS_A_VALUE -> Intersector_2
Junction_13
    -> AttributeRemover_3
AttributeCreator_19
    ATTR_TABLE = SET_TO igds_level_name (varchar(80)) = __Err_Check_ShortFeature_@Value(igds_level_name)
    -> Junction_11
Note: DGN levels NOT in XLS
AttributeCreator_18
    ATTR_TABLE = SET_TO igds_level_name (varchar(80)) = __Err__LayerNotDefined_IN_Template_@Value(igds_level_name)
    -> Junction_11
Junction_11
    -> AttributeRemover_3
DGNStyler
    COLOR_BY_LEVEL_DISPLAY = No
    COLOR_CHOICE_DISPLAY = RGB
    LINE_STYLE = 0
    LINE_WEIGHT = 8
    RGB_COLOR = 1,1,1
    DGNStyled -> BROKEN_WHITE (writer DGNV8_2)
BROKEN_WHITE (writer DGNV8_2)

Bookmark: lOCKED & SNAPPABLE CHECK
TestFilter_42
    DEFAULT_VALUE = <UNFILTERED>
    PASSED_TEST_GROUP_OUTPUT = FIRST
    TEST_LIST = "BOOL_OP,OR,COMPOSITE_TEST,""""""1"""""",TEST_CLAUSE,TEST igds_snappable != yes",igds_snappable = yes
    <UNFILTERED> -> AttributeCreator_32
AttributeCreator_32
    ATTR_TABLE = SET_TO igds_level_name (varchar(200)) = __Error_Check_ElementSnappable_
    -> Junction_7
TestFilter_43
    DEFAULT_VALUE = <UNFILTERED>
    PASSED_TEST_GROUP_OUTPUT = FIRST
    TEST_LIST = "BOOL_OP,OR,COMPOSITE_TEST,""""""1"""""",TEST_CLAUSE,TEST @Value(igds_element_locked) = yes",@Value(igds_element_locked) = yes
    @Value(igds_element_locked) = yes -> AttributeCreator_33
AttributeCreator_33
    ATTR_TABLE = SET_TO igds_level_name (varchar(200)) = __Error_Check_ElementLocked_
    -> Junction_11

Bookmark: unConnected Linear Features
AttributeFilter
    ATTR_NAME = fme_feature_type
    ATTR_VALUES = <Empty>,<Missing>,<Null>,<Unfiltered>,BackOfSidewalk,BROKEN_WHITE,BROKEN_YELLOW,CURB_BACK,CURB_BOTTOM,CURB_FRONT,CURB_TOP,DOTTED_WHITE,DOTTED_YELLOW,EOP,FrontOfSidewalk,SOLID_WHITE,SOLID_YELLOW
    BackOfSidewalk -> NodeValence [Line]
    BROKEN_WHITE -> NodeValence_2 [Line]
    BROKEN_YELLOW -> NodeValence_3 [Line]
    CURB_BACK -> NodeValence_9 [Line]
    CURB_BACK -> NeighborFinder_3 [BASE]
    CURB_BACK -> Chopper_4
    CURB_BOTTOM -> NodeValence_10 [Line]
    CURB_BOTTOM -> NeighborFinder [BASE]
    CURB_BOTTOM -> Chopper_2
    CURB_FRONT -> NodeValence_8 [Line]
    CURB_TOP -> NodeValence_11 [Line]
    CURB_TOP -> Chopper
    CURB_TOP -> NeighborFinder_2 [BASE]
    CURB_TOP -> Chopper_3
    CURB_TOP -> NeighborFinder_4 [BASE]
    DOTTED_WHITE -> NodeValence_4 [Line]
    DOTTED_YELLOW -> NodeValence_12 [Line]
    EOP -> NodeValence_5 [Line]
    FrontOfSidewalk -> NodeValence_6 [Line]
    SOLID_WHITE -> NodeValence_7 [Line]
    SOLID_YELLOW -> NodeValence_13 [Line]
NodeValence
    Node -> TestFilter
TestFilter
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = ,"BOOL_OP,OR,COMPOSITE_TEST,""""""1"""""",TEST_CLAUSE,TEST @Value(valence) > 2",@Value(valence) > 2
    @Value(valence) = -> Junction_2
    @Value(valence) > 2 -> Junction
NodeValence_8
    Node -> TestFilter_14
TestFilter_14
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_4
    @Value(valence) > 2 -> Junction_3
NodeValence_2
    Node -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_2
    @Value(valence) > 2 -> Junction
NodeValence_9
    Node -> TestFilter_8
TestFilter_8
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_4
    @Value(valence) > 2 -> Junction_3
NodeValence_3
    Node -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_2
    @Value(valence) > 2 -> Junction
NodeValence_10
    Node -> TestFilter_10
TestFilter_10
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_4
    @Value(valence) > 2 -> Junction_3
NodeValence_4
    Node -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_2
    @Value(valence) > 2 -> Junction
NodeValence_11
    Node -> TestFilter_11
NodeValence_5
    Node -> TestFilter_7
TestFilter_7
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_2
    @Value(valence) > 2 -> Junction
NodeValence_12
    Node -> TestFilter_15
NodeValence_6
    Node -> TestFilter_6
TestFilter_6
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_2
    @Value(valence) > 2 -> Junction
NodeValence_13
    Node -> TestFilter_9
Junction_4
    -> AttributeCreator
NodeValence_7
    Node -> TestFilter_5
TestFilter_5
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_2
    @Value(valence) > 2 -> Junction
Junction_2
    -> AttributeCreator
AttributeRemover_3
    REMOVE_ATTRS = 2DSnap,3DSnap,ConstantHeight,DGN LEVEL,Dangle,DuplicateVertex,Intersection,MissingVertexAtintersection,OverlapFeatures,OverlapSegment,PairedFeatures,PolygonDirection,SelfIntersection,ShortLines,SliverSpike,Undershoot,VertexInterval
    -> DGNStyler

Bookmark: Curb_Top_Back_Bottom Comparison
Chopper_4
    DEAGGREGATE_INPUT = Deaggregate
    MAX_VERTICES = 2
    MODE = By Vertex
    REMNANT_ATTR = _remnant
    CHOPPED -> Snipper_4
    UNTOUCHED -> Snipper_4
Snipper_4
    DEAGGREGATE_INPUT = YES
    ENDLOCATIONATTR = 80
    MEASUREMENTTYPE = 2D
    SNIPMODE = Distance (Value)
    STARTLOCATIONATTR = 20
    -> NeighborFinder_4 [CANDIDATE]
NeighborFinder_4
    CANDIDATES_FIRST = No
    INSERT_VERTEX = No
    MAX = 0.5
    MEASURES_FROM_CANDIDATE = No
    MEASURE_TYPE = Continuous
    MODE = Bases and Candidates
    TREAT_POLYGON_AS = Lines
    UNMATCHED_BASE -> AttributeCreator_8
AttributeCreator_8
    ATTR_TABLE = SET_TO igds_level_name (varchar(200)) = __Error_CurbBackWithout_Top_
    -> Junction_7
Chopper_3
    DEAGGREGATE_INPUT = Deaggregate
    MAX_VERTICES = 2
    MODE = By Vertex
    REMNANT_ATTR = _remnant
    CHOPPED -> Snipper_3
    UNTOUCHED -> Snipper_3
Snipper_3
    DEAGGREGATE_INPUT = YES
    ENDLOCATIONATTR = 80
    MEASUREMENTTYPE = 2D
    SNIPMODE = Distance (Value)
    STARTLOCATIONATTR = 20
    -> NeighborFinder_3 [CANDIDATE]
NeighborFinder_3
    CANDIDATES_FIRST = No
    INSERT_VERTEX = No
    MAX = 0.5
    MEASURES_FROM_CANDIDATE = No
    MEASURE_TYPE = Continuous
    MODE = Bases and Candidates
    TREAT_POLYGON_AS = Lines
    UNMATCHED_BASE -> AttributeCreator_7
AttributeCreator_7
    ATTR_TABLE = SET_TO igds_level_name (varchar(200)) = __Error_CurbTopWithout_Back_
    -> Junction_7
Chopper_2
    DEAGGREGATE_INPUT = Deaggregate
    MAX_VERTICES = 2
    MODE = By Vertex
    REMNANT_ATTR = _remnant
    CHOPPED -> Snipper_2
    UNTOUCHED -> Snipper_2
Snipper_2
    DEAGGREGATE_INPUT = YES
    ENDLOCATIONATTR = 80
    MEASUREMENTTYPE = 2D
    SNIPMODE = Distance (Value)
    STARTLOCATIONATTR = 20
    -> NeighborFinder_2 [CANDIDATE]
NeighborFinder_2
    CANDIDATES_FIRST = No
    INSERT_VERTEX = No
    MAX = 0.5
    MEASURES_FROM_CANDIDATE = No
    MEASURE_TYPE = Continuous
    MODE = Bases and Candidates
    TREAT_POLYGON_AS = Lines
    UNMATCHED_BASE -> AttributeCreator_6
AttributeCreator_6
    ATTR_TABLE = SET_TO igds_level_name (varchar(200)) = __Error_CurbBottomWithout_Top_
    -> Junction_7
Chopper
    DEAGGREGATE_INPUT = Deaggregate
    MAX_VERTICES = 2
    MODE = By Vertex
    REMNANT_ATTR = _remnant
    CHOPPED -> Snipper
    UNTOUCHED -> Snipper
Snipper
    DEAGGREGATE_INPUT = YES
    ENDLOCATIONATTR = 80
    MEASUREMENTTYPE = 2D
    SNIPMODE = Distance (Value)
    STARTLOCATIONATTR = 20
    -> NeighborFinder [CANDIDATE]
NeighborFinder
    CANDIDATES_FIRST = No
    INSERT_VERTEX = No
    MAX = 0.5
    MEASURES_FROM_CANDIDATE = No
    MEASURE_TYPE = Continuous
    MODE = Bases and Candidates
    TREAT_POLYGON_AS = Lines
    UNMATCHED_BASE -> AttributeCreator_5
AttributeCreator_5
    ATTR_TABLE = SET_TO igds_level_name (varchar(200)) = __Error_CurbTopWithout_Bottom_
    -> Junction_7

Bookmark: 3D SNAP CHECK
TestFilter_15
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_4
    @Value(valence) > 2 -> Junction_3
TestFilter_9
    DEFAULT_VALUE = <UNFILTERED>
    PASSED_TEST_GROUP_OUTPUT = FIRST
    TEST_LIST = "BOOL_OP,OR,COMPOSITE_TEST,""""""1"""""",TEST_CLAUSE,TEST @Value(valence) = 2",@Value(valence) = 2,"BOOL_OP,OR,COMPOSITE_TEST,""""""1"""""",TEST_CLAUSE,TEST @Value(valence) > 2",@Value(valence) > 2
    @Value(valence) = 2 -> Junction_4
    @Value(valence) > 2 -> Junction_3
Junction_3
    -> AttributeCreator_2
AttributeCreator
    ATTR_TABLE = SET_TO igds_level_name (buffer) = __Error_connect_Features
    -> AttributeRemover_3
Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    NODE -> PointOnLineOverlayer [POINT]
CoordinateExtractor_12
    IND = -1
    MODE = Specify Coordinate
    X_ATTR = _x1
    Y_ATTR = _y1
    Z_ATTR = _z1
    -> VertexCreator_2
VertexCreator_2
    MEASURE_TYPE = Continuous
    MODE_NAME = Replace with Point
    XVAL = @Value(_x1)
    YVAL = @Value(_y1)
    ZVAL = @Value(_z1)
    -> Matcher
    -> NeighborFinder_7 [CANDIDATE]
Intersector_2
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    NODE -> Matcher
CoordinateExtractor_11
    IND = 0
    MODE = Specify Coordinate
    X_ATTR = _x0
    Y_ATTR = _y0
    Z_ATTR = _z0
    -> VertexCreator
VertexCreator
    MEASURE_TYPE = Continuous
    MODE_NAME = Replace with Point
    XVAL = @Value(_x0)
    YVAL = @Value(_y0)
    ZVAL = @Value(_z0)
    -> Matcher
    -> NeighborFinder_7 [BASE]
Matcher
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCH_STRATEGY = Match Selected Attributes
    NOT_MATCHED -> AttributeCreator_23
AttributeCreator_23
    ATTR_TABLE = SET_TO igds_level_name (buffer) = __ERR_SanpCheck
    -> AttributeRemover_3

Bookmark: Missing vertex AT Intersection
AttributeCreator_2
    ATTR_TABLE = SET_TO igds_level_name (buffer) = __Error_CheckSnapConnectElements_
    -> AttributeRemover_3
TestFilter_44
    DEFAULT_VALUE = <UNFILTERED>
    PASSED_TEST_GROUP_OUTPUT = FIRST
    TEST_LIST:
      "BOOL_OP,COMPOSITE,COMPOSITE_TEST,""""""1 AND( 2 OR 3 )"""""",TEST_CLAUSE,TEST Intersection ATTRIBUTE_HAS_A_VALUE ""
      TEST $(all) = YES
      TEST $(Val) = YES",Intersection ATTRIBUTE_HAS_A_VALUE
    Intersection ATTRIBUTE_HAS_A_VALUE -> Chopper_15
    Intersection ATTRIBUTE_HAS_A_VALUE -> Intersector
    Intersection ATTRIBUTE_HAS_A_VALUE -> Matcher_3
Chopper_15
    DEAGGREGATE_INPUT = Deaggregate
    MAX_VERTICES = 2
    MODE = By Vertex
    REMNANT_ATTR = _remnant
    CHOPPED -> Snipper_6
    CHOPPED -> Bufferer
    CHOPPED -> SpatialRelator [Supplier]
    UNTOUCHED -> Bufferer
    UNTOUCHED -> SpatialRelator [Supplier]
NeighborFinder_7
    CANDIDATES_FIRST = No
    INSERT_VERTEX = No
    MAX = $(z_Tol)
    MEASURES_FROM_CANDIDATE = Yes
    MEASURE_TYPE = Continuous
    MODE = Bases and Candidates
    TREAT_POLYGON_AS = Lines
    MATCHED -> PointOnPointOverlayer_2 [POINT]
    UNMATCHED_BASE -> PointOnPointOverlayer_2 [POINT]
    UNMATCHED_CANDIDATE -> PointOnPointOverlayer_2 [POINT]
PointOnPointOverlayer_2
    DEAGGREGATE_INPUT = Yes
    OV_ATTR = _overlaps
    TOLERANCE = 0.01
    POINT -> TestFilter_46
TestFilter_46
    DEFAULT_VALUE = <UNFILTERED>
    PASSED_TEST_GROUP_OUTPUT = FIRST
    TEST_LIST = "BOOL_OP,OR,COMPOSITE_TEST,""""""1"""""",TEST_CLAUSE,TEST @Value(_overlaps) = 0",@Value(_overlaps) > 0
    @Value(_overlaps) > 0 -> AttributeCreator_34
AttributeCreator_34
    ATTR_TABLE = SET_TO igds_level_name (buffer) = __Check_for_Intersection_
    -> Junction_13

Bookmark: Snap 2D check
Intersector_3
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Matcher_4
    <REJECTED> -> TestFilter_36
CoordinateExtractor_10
    IND = 0
    MODE = Specify Coordinate
    X_ATTR = _x
    Y_ATTR = _y
    Z_ATTR = _z
    -> VertexCreator_3
VertexCreator_3
    MEASURE_TYPE = Continuous
    MODE_NAME = Replace with Point
    XVAL = @Value(_x)
    YVAL = @Value(_y)
    ZVAL = @Value(_z)
    -> Matcher_4
CoordinateExtractor_6
    IND = -1
    MODE = Specify Coordinate
    X_ATTR = _x1
    Y_ATTR = _y1
    Z_ATTR = _z1
    -> VertexCreator_4
VertexCreator_4
    MEASURE_TYPE = Continuous
    MODE_NAME = Replace with Point
    XVAL = @Value(_x1)
    YVAL = @Value(_y1)
    ZVAL = @Value(_z1)
    -> Matcher_4
Matcher_4
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCH_STRATEGY = Match Selected Attributes
    MATCHED -> AttributeCreator_28
Chopper_14
    DEAGGREGATE_INPUT = Deaggregate
    MAX_VERTICES = 1
    MODE = By Vertex
    REMNANT_ATTR = _remnant
    CHOPPED -> Counter_3
    UNTOUCHED -> Counter_3
Counter_3
    CNT_ATTR = _countC
    DOMAIN = counter
    SCOPE = Global
    START = 0
    -> CoordinateExtractor_9
CoordinateExtractor_9
    IND = 0
    MODE = Specify Coordinate
    Z_ATTR = _z_vertex
    -> TestFilter_36
TestFilter_36
    DEFAULT_VALUE = <UNFILTERED>
    PASSED_TEST_GROUP_OUTPUT = FIRST
    TEST_LIST:
      "BOOL_OP,OR,COMPOSITE_TEST,""""""1 OR 2"""""",TEST_CLAUSE,TEST @Value(_z_vertex) = 0
      TEST _z_vertex ATTRIBUTE_IS_MISSING """,@Value(_z_vertex) = 0
    <UNFILTERED> -> AttributeRounder_4
AttributeRounder_4
    PLACES = 2
    ROUND_TYPE = Nearest
    SRC_ATTRS = _z_vertex
    -> Clipper_2 [CANDIDATE]
Counter_2
    CNT_ATTR = _count
    DOMAIN = counter
    SCOPE = Global
    START = 0
    -> AttributeKeeper_2
    -> CoordinateExtractor_8
CoordinateExtractor_8
    LIST_NAME = _indices
    MODE = All Coordinates
    -> ListExploder_3
ListExploder_3
    ATTR_ACCUM_MODE = Merge List Attributes
    ATTR_CONFLICT_RES = Use List Attribute Values
    INDEX_ATTR = _element_index
    LIST_ATTR = _indices{}
    ELEMENTS -> StatisticsCalculator_2
StatisticsCalculator_2
    CALCULATION_MODE = NUMERIC
    FEAT_STATS = z,NUMERIC_MODE,MIN,MAX,,,,,,,,,,,
    GROUP_BY = _count
    SUMMARY -> AttributeRounder_3
AttributeRounder_3
    PLACES = 2
    ROUND_TYPE = Nearest
    SRC_ATTRS = z.max z.min
    -> AttributeCreator_27
AttributeCreator_27
    ATTR_TABLE:
      SET_TO _z_min (real64) = @Value(z.min)
      SET_TO _z_max (real64) = @Value(z.max)
    -> AttributeKeeper_3
AttributeKeeper_3
    CREATE_BULK_MODE_FEATURES = NO
    KEEP_ATTRS = z.max,z.min,_count,_z_max,_z_min
    -> FeatureJoiner_3 [RIGHT]
AttributeKeeper_2
    CREATE_BULK_MODE_FEATURES = NO
    KEEP_ATTRS = _count
    -> FeatureJoiner_3 [LEFT]
FeatureJoiner_3
    ATTR_CONFLICT_RES = Prefer Left
    GEOMETRY_HANDLING = Prefer Left
    JOIN_KEYS = _count _count AUTO
    JOIN_MODE = Inner
    JOINED -> Clipper_2 [CLIPPER]
Clipper_2
    ADD_NODATA = YES
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> TestFilter_37
TestFilter_37
    DEFAULT_VALUE = <UNFILTERED>
    PASSED_TEST_GROUP_OUTPUT = FIRST
    TEST_LIST:
      "BOOL_OP,OR,COMPOSITE_TEST,""""""1 OR 2"""""",TEST_CLAUSE,TEST @Value(_z_vertex) < @Value(_z_min)-5
      TEST @Value(_z_vertex) > @Value(_z_max)+5",@Value(_z_vertex) < @Value(_z_min)-5
    @Value(_z_vertex) < @Value(_z_min)-5 -> AttributeCreator_28
AttributeCreator_28
    ATTR_TABLE = SET_TO igds_level_name (buffer) = __Check_for_Elevation_Diff
    -> Junction_13

Bookmark: Vertex Distance StraightLine and Cuvered Lines
Chopper_5
    DEAGGREGATE_INPUT = Deaggregate
    MAX_VERTICES = 3
    MODE = By Vertex
    REMNANT_ATTR = _remnant
    CHOPPED -> LengthCalculator
    UNTOUCHED -> LengthCalculator
LengthCalculator
    DIM = 2
    LEN_ATTR = _length
    MULT = 1
    -> AngularityCalculator
    -> TestFilter_18
AngularityCalculator
    ANG_ATTR = _angularity
    -> TestFilter_13
TestFilter_13
    DEFAULT_VALUE = <UNFILTERED>
    PASSED_TEST_GROUP_OUTPUT = FIRST
    TEST_LIST = "BOOL_OP,OR,COMPOSITE_TEST,""""""1"""""",TEST_CLAUSE,TEST @Value(_angularity) > 3",@Value(_angularity) > 3
    @Value(_angularity) > 3 -> LineCombiner
    <UNFILTERED> -> Chopper_7
LineCombiner
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Chopper_6
Chopper_6
    DEAGGREGATE_INPUT = Deaggregate
    MAX_VERTICES = 2
    MODE = By Vertex
    REMNANT_ATTR = _remnant
    CHOPPED -> LengthCalculator_3
    UNTOUCHED -> LengthCalculator_3
LengthCalculator_3
    DIM = 2
    LEN_ATTR = _length1
    MULT = 1
    -> TestFilter_16
TestFilter_16
    DEFAULT_VALUE = <UNFILTERED>
    PASSED_TEST_GROUP_OUTPUT = FIRST
    TEST_LIST = "BOOL_OP,OR,COMPOSITE_TEST,""""""1"""""",TEST_CLAUSE,TEST @Value(_length1) > 1.8",@Value(_length) > .5
    <UNFILTERED> -> AttributeCreator_9
AttributeCreator_9
    ATTR_TABLE = SET_TO igds_level_name (varchar(200)) = __Error_Check_SegmentDistanceAtCurves_
    -> Junction_6
Chopper_7
    DEAGGREGATE_INPUT = Deaggregate
    MAX_VERTICES = 2
    MODE = By Vertex
    REMNANT_ATTR = _remnant
    CHOPPED -> LengthCalculator_2
    UNTOUCHED -> LengthCalculator_2
LengthCalculator_2
    DIM = 2
    LEN_ATTR = _length2
    MULT = 1
    -> TestFilter_17
TestFilter_17
    DEFAULT_VALUE = <UNFILTERED>
    PASSED_TEST_GROUP_OUTPUT = FIRST
    TEST_LIST = "BOOL_OP,OR,COMPOSITE_TEST,""""""1"""""",TEST_CLAUSE,TEST @Value(_length2) > $(vertex_Tol)",@Value(_length) > .5
    @Value(_length) > .5 -> AttributeCreator_10
AttributeCreator_10
    ATTR_TABLE = SET_TO igds_level_name (varchar(200)) = __Error_Check_Segment_DistanceAtStraightLines_
    -> Junction_6
TestFilter_18
    DEFAULT_VALUE = <UNFILTERED>
    PASSED_TEST_GROUP_OUTPUT = FIRST
    TEST_LIST = "BOOL_OP,OR,COMPOSITE_TEST,""""""1"""""",TEST_CLAUSE,TEST @Value(_length) < .1",@Value(_length) > .5
    @Value(_length) > .5 -> AttributeCreator_13
AttributeCreator_13
    ATTR_TABLE = SET_TO igds_level_name (varchar(200)) = __Error_Check_ShortLines_
    -> Junction_6
Junction_6
    -> Junction_7

Bookmark: Elevation Diff between vertices-Spike - Monotony
GeometryCoercer
    GQUERY:
      for $geom in //geometry
      where $geom/count(parent::geometry) = 0
      return number($geom/@fme_id)
    KIND = fme_line
    COERCED -> ZigzagRemover
ZigzagRemover
    MAX_ANGLE = 15
    REPLACE_SEGMENT = No
    SPIKE_CREATION = Line Segments forming Spike
    SPIKE_LENGTH_IS = Longer Segment
    Spike -> AttributeCreator_12
SpikeRemover
    DIMENSIONS = 2D
    ITERATIVE = Yes
    SPIKEANGLE = 15
    REMOVED -> AttributeCreator_12
Chopper_8
    DEAGGREGATE_INPUT = Deaggregate
    MAX_VERTICES = 2
    MODE = By Vertex
    REMNANT_ATTR = _remnant
    CHOPPED -> CoordinateExtractor
    UNTOUCHED -> CoordinateExtractor
CoordinateExtractor
    IND = 0
    MODE = Specify Coordinate
    X_ATTR = _x0
    Y_ATTR = _y0
    Z_ATTR = _z0
    Z_DEFAULT = -999
    -> CoordinateExtractor_2
CoordinateExtractor_2
    IND = -1
    MODE = Specify Coordinate
    X_ATTR = _x1
    Y_ATTR = _y1
    Z_ATTR = _z1
    Z_DEFAULT = -999
    -> AttributeCreator_11
AttributeCreator_11
    ATTR_TABLE = SET_TO Elev_Diff (varchar(200)) = @Evaluate(@Value(_z1)-@Value(_z0))
    -> Tester
Tester
    BOOL_OP = OR
    TEST_CLAUSE = TEST @Value(Elev_Diff) > 10
    TEST_MODE = TEST
    PASSED -> AttributeCreator_12
AttributeCreator_12
    ATTR_TABLE = SET_TO igds_level_name (varchar(200)) = __Error_CheckForSpike_
    -> Junction_6

Bookmark: Elevation Difference at Vertices
Chopper_9
    DEAGGREGATE_INPUT = Deaggregate
    MAX_VERTICES = 1
    MODE = By Vertex
    REMNANT_ATTR = _remnant
    CHOPPED -> CoordinateExtractor_3
    UNTOUCHED -> CoordinateExtractor_3
CoordinateExtractor_3
    IND = 0
    MODE = Specify Coordinate
    Z_ATTR = _z_vertex
    -> TestFilter_19
TestFilter_19
    DEFAULT_VALUE = <UNFILTERED>
    PASSED_TEST_GROUP_OUTPUT = FIRST
    TEST_LIST:
      "BOOL_OP,OR,COMPOSITE_TEST,""""""1 OR 2"""""",TEST_CLAUSE,TEST @Value(_z_vertex) = 0
      TEST _z_vertex ATTRIBUTE_IS_MISSING """,@Value(_z_vertex) = 0
    @Value(_z_vertex) = 0 -> AttributeRounder
AttributeRounder
    PLACES = 2
    ROUND_TYPE = Nearest
    SRC_ATTRS = _z_vertex
    -> Clipper [CANDIDATE]
Counter
    CNT_ATTR = _count
    DOMAIN = counter
    GRP_CNT_ATTR = _countFeature
    SCOPE = Global
    START = 0
    -> CoordinateExtractor_4
    -> AttributeKeeper
AttributeKeeper
    CREATE_BULK_MODE_FEATURES = NO
    KEEP_ATTRS = igds_level_name,_count
    -> FeatureJoiner [LEFT]
CoordinateExtractor_4
    LIST_NAME = _AllCoord
    MODE = All Coordinates
    -> ListExploder
ListExploder
    ATTR_ACCUM_MODE = Merge List Attributes
    ATTR_CONFLICT_RES = Use List Attribute Values
    LIST_ATTR = _AllCoord{}
    ELEMENTS -> StatisticsCalculator
StatisticsCalculator
    CALCULATION_MODE = NUMERIC
    FEAT_STATS = z,NUMERIC_MODE,MIN,MAX,,,,,,,,,,,
    GROUP_BY = _count
    SUMMARY -> AttributeRounder_2
AttributeRounder_2
    PLACES = 2
    ROUND_TYPE = Nearest
    SRC_ATTRS = z.max z.min
    -> FeatureJoiner [RIGHT]
FeatureJoiner
    ATTR_CONFLICT_RES = Prefer Left
    GEOMETRY_HANDLING = Prefer Left
    JOIN_KEYS = _count _count AUTO
    JOIN_MODE = Inner
    JOINED -> Clipper [CLIPPER]
Clipper
    ADD_NODATA = YES
    ATTR_ACCUM_MODE = MERGE
    ATTR_CONFLICT_RES = CANDIDATE
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> TestFilter_20
TestFilter_20
    DEFAULT_VALUE = <UNFILTERED>
    PASSED_TEST_GROUP_OUTPUT = FIRST
    TEST_LIST:
      "BOOL_OP,OR,COMPOSITE_TEST,""""""1 OR 2"""""",TEST_CLAUSE,TEST @Value(_z_vertex) < @Value(z.min)-5
      TEST @Value(_z_vertex) > @Value(z.max)+5",@Value(_z_vertex) < @Value(z.min)-5
    @Value(_z_vertex) < @Value(z.min)-5 -> AttributeCreator_14
AttributeCreator_14
    ATTR_TABLE = SET_TO igds_level_name (buffer) = __Error_checkForElevationDiff
    -> Junction_6

Bookmark: Paired Elements Check
AttributeExposer
    ATTR_LIST = igds_model_name
    -> Aggregator
Aggregator
    ACCUM_ATTRS_NAME = Drop Incoming Attributes
    AGGREGATE_TYPE = Homogeneous Collection (If Possible)
    GROUP_BY = PairedFeatures
    MODE = Geometry - Assemble One Level
    SEP = ,
    AGGREGATE -> TestFilter_26
TestFilter_26
    DEFAULT_VALUE = <UNFILTERED>
    PASSED_TEST_GROUP_OUTPUT = FIRST
    TEST_LIST = "BOOL_OP,AND,COMPOSITE_TEST,""""""1"""""",TEST_CLAUSE,TEST PairedFeatures ATTRIBUTE_HAS_A_VALUE """,PairedFeatures ATTRIBUTE_HAS_A_VALUE
    PairedFeatures ATTRIBUTE_HAS_A_VALUE -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Chopper_10
Chopper_10
    DEAGGREGATE_INPUT = Deaggregate
    MAX_VERTICES = 2
    MODE = By Vertex
    REMNANT_ATTR = _remnant
    CHOPPED -> Snipper_5
Snipper_5
    DEAGGREGATE_INPUT = YES
    ENDLOCATIONATTR = 80
    MEASUREMENTTYPE = 2D
    SNIPMODE = Distance (Value)
    STARTLOCATIONATTR = 20
    -> NeighborFinder_5 [BASE]
    -> NeighborFinder_5 [CANDIDATE]
NeighborFinder_5
    CANDIDATES_FIRST = No
    GROUP_BY = PairedFeatures
    INSERT_VERTEX = No
    MAX = $(pair_Tol)
    MEASURES_FROM_CANDIDATE = Yes
    MEASURE_TYPE = Continuous
    MODE = Bases and Candidates
    TREAT_POLYGON_AS = Lines
    UNMATCHED_BASE -> AttributeCreator_15
    UNMATCHED_CANDIDATE -> AttributeCreator_15
AttributeCreator_15
    ATTR_TABLE = SET_TO igds_level_name (varchar(200)) = __Err_PairElement_Not_match_@Value(PairedFeatures)
    -> Junction_11
TestFilter_24
    DEFAULT_VALUE = <UNFILTERED>
    PASSED_TEST_GROUP_OUTPUT = FIRST
    TEST_LIST = "BOOL_OP,OR,COMPOSITE_TEST,""""""1"""""",TEST_CLAUSE,TEST @Value(PolygonDirection) = CCW",left,"BOOL_OP,OR,COMPOSITE_TEST,""""""1"""""",TEST_CLAUSE,TEST @Value(PolygonDirection) = CW",right
    left -> GeometryValidator_3
    right -> GeometryValidator_4
GeometryValidator_3
    ISSUE_ATTR_NAME = _issues
    PRESETS = Custom
    REPAIR = No
    RULES = AREA_ORIENTATION AREA_ORIENTATION]LEFT]FME_CONTROLLER_QUERY_FILE]transformers/dependencies/geometryvalidator8/AREA_ORIENTATION.fme]FME_CONTROLLER_CHOICE]AREA_ORIENTATION
    SUMMARY = Detailed
    ISSUE_LOCATIONS -> AttributeCreator_29
AttributeCreator_29
    ATTR_TABLE = SET_TO igds_level_name (varchar(80)) = __Err_Check_@Value(issue_found)
    -> Junction_12

Bookmark: Geoemtry Check
TestFilter_33
    DEFAULT_VALUE = <UNFILTERED>
    PASSED_TEST_GROUP_OUTPUT = FIRST
    TEST_LIST:
      "BOOL_OP,COMPOSITE,COMPOSITE_TEST,""""""1 AND( 2 OR 3 )"""""",TEST_CLAUSE,TEST Geometry ATTRIBUTE_HAS_A_VALUE ""
      TEST $(all) = YES
      TEST $(Geo) = YES",GeometryCheck
    GeometryCheck -> SequenceMatcher
SequenceMatcher
    AttributeA = @Value(igds_type)
    AttributeB = @Value(Geometry)
    -> Tester_2
Tester_2
    BOOL_OP = OR
    TEST_CLAUSE = CASE_INSENSITIVE_TEST @Value(_ratio) != 1
    TEST_MODE = CASE_INSENSITIVE_TEST
    PASSED -> AttributeCreator_38
AttributeCreator_38
    ATTR_TABLE = SET_TO igds_level_name (buffer) = __Err_Geometry_Not_match_
    -> Junction_6
Junction_12
    -> Junction_11

Bookmark: Slef-intersection check
GeometryValidator
    ISSUE_ATTR_NAME = _issues
    PRESETS = Custom
    REPAIR = No
    RULES = TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR OGC_VALID_CHECK OGC_VERSION]V1.2.0]LEGACY_OGC]No]FME_CONTROLLER_QUERY_FILE]transformers/dependencies/geometryvalidator8/OGC_VALID_CHECK.fme]FME_CONTROLLER_CHOICE]OGC_VALID_CHECK MISSING_VERTEX_NORMALS FME_CONTROLLER_QUERY_FILE]transformers/dependencies/geometryvalidator8/MISSING_VERTEX_NORMALS.fme]FME_CONTROLLER_CHOICE]MISSING_VERTEX_NORMALS CONSECUTIVE_IDENTICAL_VERTICES_2D CHECK_Z]NO]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SELF_INTERSECTING CHECK_HOLE_TOUCHING_POLYGON]Yes]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING OGC_SIMPLE_CHECK LEGACY_OGC]No]FME_CONTROLLER_QUERY_FILE]transformers/dependencies/geometryvalidator8/OGC_SIMPLE_CHECK.fme]FME_CONTROLLER_CHOICE]OGC_SIMPLE_CHECK
    SUMMARY = Detailed
    ISSUE_LOCATIONS -> TestFilter_12
TestFilter_12
    DEFAULT_VALUE = <UNFILTERED>
    PASSED_TEST_GROUP_OUTPUT = FIRST
    TEST_LIST = "BOOL_OP,OR,COMPOSITE_TEST,""""""1"""""",TEST_CLAUSE,CASE_INSENSITIVE_TEST @Value(issue_found) LIKE Self Intersection",@Value(issue_found) =
    @Value(issue_found) = -> AttributeCreator_3
    <UNFILTERED> -> AttributeCreator_4
AttributeCreator_3
    ATTR_TABLE = SET_TO igds_level_name (buffer) = __Error_InterSection_
    -> Junction_5
AttributeCreator_4
    ATTR_TABLE = SET_TO igds_level_name (varchar(80)) = __Error_LinearFeatureError_@Value(issue_found)_
    -> Junction_5

Bookmark: OverlapFeatures
Bufferer
    ANGLE = 22.5
    CAP_STYLE = Arc
    CORNER_STYLE = Arc
    MODE = AREA
    OFFSET = .01
    OFFSET_UNITS = NONE
    PRECISION = APPROX
    BUFFERED -> SpatialRelator [Requestor]
SpatialRelator
    AGGREGATE_HANDLING = Yes
    CALC_CARD = No
    CURVE_BOUNDARY_RULE_PARAM = Default Rule
    LIST_NAME = _relationships
    PREDICATES = CONTAINS
    SUCCESS_ATTR = _related_suppliers
    -> TestFilter_45
TestFilter_45
    DEFAULT_VALUE = <UNFILTERED>
    PASSED_TEST_GROUP_OUTPUT = FIRST
    TEST_LIST = "BOOL_OP,OR,COMPOSITE_TEST,""""""1"""""",TEST_CLAUSE,TEST @Value(_related_suppliers) >= 2",@Value(_related_suppliers) >= 2
    @Value(_related_suppliers) >= 2 -> AttributeCreator_37
AttributeCreator_37
    ATTR_TABLE = SET_TO igds_level_name (buffer) = __Check_for_OverlapSegment_
    -> Junction_13
Matcher_3
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCH_STRATEGY = Match Selected Attributes
    SINGLE_MATCHED -> AttributeCreator_36
AttributeCreator_36
    ATTR_TABLE = SET_TO igds_level_name (buffer) = __Check_for_OverlapFeatures_
    -> Junction_13

Bookmark: Polygon Direction Check check for constant Elevation of Polygons
TestFilter_38
    DEFAULT_VALUE = <UNFILTERED>
    PASSED_TEST_GROUP_OUTPUT = FIRST
    TEST_LIST = "BOOL_OP,AND,COMPOSITE_TEST,""""""1"""""",TEST_CLAUSE,TEST @Value(igds_type) = igds_shape",@Value(igds_level) = area
    @Value(igds_level) = area -> TestFilter_24
    @Value(igds_level) = area -> TestFilter_41
GeometryValidator_4
    ISSUE_ATTR_NAME = _issues
    PRESETS = Custom
    REPAIR = No
    RULES = AREA_ORIENTATION AREA_ORIENTATION]RIGHT]FME_CONTROLLER_QUERY_FILE]transformers/dependencies/geometryvalidator8/AREA_ORIENTATION.fme]FME_CONTROLLER_CHOICE]AREA_ORIENTATION
    SUMMARY = Detailed
    ISSUE_LOCATIONS -> AttributeCreator_30
AttributeCreator_30
    ATTR_TABLE = SET_TO igds_level_name (varchar(80)) = __Err_Check_@Value(issue_found)
    -> Junction_12
TestFilter_41
    DEFAULT_VALUE = <UNFILTERED>
    PASSED_TEST_GROUP_OUTPUT = FIRST
    TEST_LIST = "BOOL_OP,OR,COMPOSITE_TEST,""""""1"""""",TEST_CLAUSE,TEST ConstantHeight ATTRIBUTE_HAS_A_VALUE """,@Value(PolygonDirection) =ConstantHeight
    @Value(PolygonDirection) =ConstantHeight -> GeometryValidator_5
GeometryValidator_5
    ISSUE_ATTR_NAME = _issues
    PRESETS = Custom
    REPAIR = No
    RULES = PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE
    SUMMARY = Detailed
    ISSUE_LOCATIONS -> AttributeCreator_31
AttributeCreator_31
    ATTR_TABLE = SET_TO igds_level_name (varchar(80)) = __Err_Check_@Value(issue_found)
    -> Junction_12

Bookmark: Basic Validation
GeometryValidator_2
    ISSUE_ATTR_NAME = _issues
    PRESETS = Custom
    REPAIR = No
    RULES = CONSECUTIVE_IDENTICAL_VERTICES_2D CHECK_Z]YES]TOLERANCE]0.01]FME_CONTROLLER_QUERY_FILE]transformers/dependencies/geometryvalidator8/CONSECUTIVE_IDENTICAL_VERTICES_2D.fme]FME_CONTROLLER_CHOICE]CONSECUTIVE_IDENTICAL_VERTICES_2D MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS MISSING_VERTEX_NORMALS FME_CONTROLLER_QUERY_FILE]transformers/dependencies/geometryvalidator8/MISSING_VERTEX_NORMALS.fme]FME_CONTROLLER_CHOICE]MISSING_VERTEX_NORMALS SELF_INTERSECTING CHECK_HOLE_TOUCHING_POLYGON]Yes]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    ISSUE_LOCATIONS -> AttributeCreator_16
AttributeCreator_16
    ATTR_TABLE = SET_TO igds_level_name (varchar(80)) = __Err_Check_@Value(issue_found)
    -> Junction_11

Bookmark: ShortSegement check
TestFilter_30
    DEFAULT_VALUE = <UNFILTERED>
    PASSED_TEST_GROUP_OUTPUT = FIRST
    TEST_LIST:
      "BOOL_OP,COMPOSITE,COMPOSITE_TEST,""""""1 AND( 2 OR 3 )"""""",TEST_CLAUSE,TEST ShortLines ATTRIBUTE_HAS_A_VALUE ""
      TEST $(all) = YES
      TEST $(Val) = YES",shortlines
    shortlines -> LengthCalculator_4
    shortlines -> Chopper_12
LengthCalculator_4
    DIM = 2
    LEN_ATTR = _length
    MULT = 1
    -> TestFilter_31
TestFilter_31
    DEFAULT_VALUE = <UNFILTERED>
    PASSED_TEST_GROUP_OUTPUT = FIRST
    TEST_LIST = "BOOL_OP,OR,COMPOSITE_TEST,""""""1"""""",TEST_CLAUSE,TEST @Value(_length) < 0.1",@Value(_length) < 0.1
    @Value(_length) < 0.1 -> AttributeCreator_19
Chopper_12
    DEAGGREGATE_INPUT = Deaggregate
    MAX_VERTICES = 2
    MODE = By Vertex
    REMNANT_ATTR = _remnant
    CHOPPED -> LengthCalculator_5
    UNTOUCHED -> LengthCalculator_5
LengthCalculator_5
    DIM = 2
    LEN_ATTR = _length
    MULT = 1
    -> TestFilter_32
TestFilter_32
    DEFAULT_VALUE = <UNFILTERED>
    PASSED_TEST_GROUP_OUTPUT = FIRST
    TEST_LIST = "BOOL_OP,OR,COMPOSITE_TEST,""""""1"""""",TEST_CLAUSE,TEST @Value(_length) < 0.1",@Value(_length) < 0.1
    @Value(_length) < 0.1 -> AttributeCreator_20
AttributeCreator_20
    ATTR_TABLE = SET_TO igds_level_name (buffer) = __Err_Check_ShortSegment_
    -> Junction_11

Bookmark: Dangle Nodes Check
NodeValence_14
    Node -> TestFilter_48
TestFilter_48
    DEFAULT_VALUE = <UNFILTERED>
    PASSED_TEST_GROUP_OUTPUT = FIRST
    TEST_LIST = "BOOL_OP,OR,COMPOSITE_TEST,""""""1"""""",TEST_CLAUSE,TEST @Value(valence) != 1",@Value(valence) != 1
    @Value(valence) != 1 -> NeighborFinder_8 [CANDIDATE]
NeighborFinder_8
    INSERT_VERTEX = No
    MAX = $(xy_Tol)
    MEASURES_FROM_CANDIDATE = Yes
    MEASURE_TYPE = Continuous
    MODE = Candidates Only
    TREAT_POLYGON_AS = Lines
    MATCHED -> AttributeCreator_39
AttributeCreator_39
    ATTR_TABLE = SET_TO igds_level_name (buffer) = __Error_DangleVertex_
    -> Junction_11

Bookmark: Negative Elevation check
Chopper_11
    DEAGGREGATE_INPUT = Deaggregate
    MAX_VERTICES = 1
    MODE = By Vertex
    REMNANT_ATTR = _remnant
    CHOPPED -> CoordinateExtractor_5
    UNTOUCHED -> CoordinateExtractor_5
CoordinateExtractor_5
    IND = 0
    MODE = Specify Coordinate
    X_ATTR = _x
    Y_ATTR = _y
    Z_ATTR = _z
    -> TestFilter_29
TestFilter_29
    DEFAULT_VALUE = <UNFILTERED>
    PASSED_TEST_GROUP_OUTPUT = FIRST
    TEST_LIST = "BOOL_OP,OR,COMPOSITE_TEST,""""""1"""""",TEST_CLAUSE,TEST @Value(_z) > 0",greater than 0
    <UNFILTERED> -> AttributeCreator_17
AttributeCreator_17
    ATTR_TABLE = SET_TO igds_level_name (buffer) = __Err_Check_Negative_value
    -> Junction_11

Bookmark: Duplicate Segment check
Chopper_13
    DEAGGREGATE_INPUT = Deaggregate
    MAX_VERTICES = 2
    MODE = By Vertex
    REMNANT_ATTR = _remnant
    CHOPPED -> Matcher_2
    UNTOUCHED -> Matcher_2
CoordinateExtractor_7
    IND = 0
    MODE = Specify Coordinate
    X_ATTR = _x
    Y_ATTR = _y
    Z_ATTR = _z
    -> AttributeCreator_25
AttributeCreator_25
    ATTR_TABLE:
      SET_TO XX (varchar(200)) = @round(@Value(@XValue()),2)
      SET_TO YY (varchar(200)) = @round((@YValue()),2)
      SET_TO ZZ (varchar(200)) = @round(@Value(@ZValue()),2)
    -> Matcher_2
Matcher_2
    BLANK_AND_MISSING_DIFFER = No
    BLANK_AND_MISSING_NAMES_TRAITS_DIFFER = No
    CHECK_COORDINATE_SYSTEMS = No
    CHECK_TYPES_AND_ENCODINGS = No
    CNT_ATTR = _match_id
    DIFFATTRS = igds_level_name
    LENIENT_MATCH = Yes
    MATCH = FULL
    MATCHATTRS = igds_level_name XX YY ZZ
    MATCH_STRATEGY = Match Selected Attributes
    SINGLE_MATCHED -> AttributeCreator_26
AttributeCreator_26
    ATTR_TABLE = SET_TO igds_level_name (buffer) = __Error_duplicateSegments
    -> Junction_11

FME custom transformer ZigzagRemover
Removes spikes and duplicate vertices from a line, polygon and donut. Basically works like the SpikeRemover, but this transformer can also remove two or more consecutive spikes forming 
    zigzag
    shape.
    This transformer supports Line, Path, Polygon and Donut geometries, except one containing a non-linear (arc) part. Aggregate and multi geometries are not supported. Input features that have unsupported geometry will be output through the <Rejected> port.
    Note: This transformer accepts 2D and 3D line, polygon and donut. However, the angle and length always will be computed in 2D. As well, consecutive vertices will also be compared in 2D. If consecutive vertices have the same (x, y), this transformer determines that those are duplicate vertices even if their z-coordinates are different.
    Note: This transformer will not guarantee that the resulting geometry is clean. Removing spikes could cause some other issues such as self-intersections. Consider using the GeometryValidator in conjunction with this transformer to check if such an issue has occurred.
Output ports
    Unchanged
    : 
    If no vertices have been removed, the input feature will be output through the Unchanged port, except the <Rejected> case. 
    Changed
    : 
    If one or more vertices have been removed, the resultant feature will be output through the Changed port, except the Degenerated case.
    Output features from this port will have 2 new attributes: 
    _num_spikes
    (number of removed spikes) and 
    _num_duplicates
    (number of removed duplicate vertices). 
    Degenerated
    : 
    If the geometry has degenerated by removing spikes, the feature will be output through the Degenerated port. The degenerated features may have a Point or Line, or may not have a geometry. A donut whose holes have degenerated will also be output through this port.
    Output features from this port will have 2 new attributes:
    _num_spikes
    (number of removed spikes) and 
    _num_duplicates
    (number of removed duplicate vertices).
    Note: A donut will be output through the Degenerated port if one or more of its parts including holes has degenerated.
    If the outer shell has degenerated, all the holes will be discarded. Otherwise, degenerated holes only will be discarded. 
    Spike
    : 
    By default, removed spike vertices (points) will be output through the Spike port. Optionally you can set "Line Segments forming Spike" to the "Spike Feature Creation" parameter, so that segments (lines) that have formed spikes will be output through this port. If you don't need to create spike features, set "None" to the parameter. 
    Output features from this port will have 3 new attributes: 
    _spike_angle
    (angle of the spike, in degrees), 
    _spike_length1
    (length of the first segment forming the spike) and 
    _spike_length2
    (length of the second segment forming the spike). 
    Duplicate
    : 
    Removed duplicate vertices (points) will be output through the Duplicate port. 
    <Rejected>
    : 
    If the geometry of the input feature is not supported by this transformer, it will be output through the <Rejected> port.
    Output features from this port will have a new attribute: 
    _rejected_reason
    (description on the rejected reason).
    Parameters
    Maximum Spike Angle
    : 
    If the angle (in degrees) between two line segments is less than or equal to this parameter, then the middle vertex is a spike and is removed. This parameter value has to be greater than or equal to 0 and less than 90 degrees.
    Maximum Spike Length
    : 
    If this parameter is specified, this transformer will not remove spikes whose length is greater than this parameter value. Otherwise every spike will be removed. This parameter value has to be greater than 0, or <blank>.
    The length of a spike will be determined by the lengths of two line segments forming the spike, with a way according to the "Determine Spike Length With" parameter setting. 
    Determine Spike Length With
    : 
    By default, this transformer considers the length of longer one of the two line segments as the spike length. Optionally you can change the behavior to "Shorter Segment" or "Average of Two Segments" with this parameter.
    This parameter will not be used if the "Maximum Spike Length" parameter is not set.
    Spike Feature Creation
    : 
    With this parameter, you can control how the removed spikes should be treated. Choices are: 
    "None": Spike vertices will be consumed. i.e. no features will be output through the Spike port. 
    "Point of Spike Vertex" (default): Spike vertices will be output through the Spike port. 
    "Line Segments forming Spike": Line that consists of two segments forming a spike will be output through the Spike port for each spike.
    Replace Segment between Spike Vertices with Vertex
    : 
    By default, all line segments forming one or more consecutive spikes will be replaced with a segment between start and end vertices of the spike(s). If you set "Yes" to this parameter, each segment between two spike vertices will be replaced with a new vertex located on its midpoint.

Parameters:
- MAX_ANGLE =   # Maximum Spike Angle (0 <= and < 90 degrees)
- MAX_LENGTH =   # Maximum Spike Length (2D)
- SPIKE_LENGTH_IS = Longer Segment   # "Longer Segment"%"Shorter Segment"%"Average of Two Segments" Determine Spike Length With
- SPIKE_CREATION = Point of Spike Vertex   # of Spike Vertex"%"Line Segments forming Spike" Spike Feature Creation
- REPLACE_SEGMENT = No   # Replace Segment between Spike Vertices with Vertex

Input (input)
    -> ParameterFetcher
ParameterFetcher
    ATTR_LIST = __zspikeremover.maxangle {$(MAX_ANGLE)} __zspikeremover.maxlength {$(MAX_LENGTH)} __zspikeremover.spike_length_is {$(SPIKE_LENGTH_IS)} __zspikeremover.spike_creation {$(SPIKE_CREATION)} __zspikeremover.replace_segment {$(REPLACE_SEGMENT)}
    -> PythonCaller
PythonCaller
    NEW_ATTRIBUTES = __zspikeremover.flag _rejected_reason _spike_angle _spike_length1 _spike_length2 _num_spikes _num_duplicates
    PYTHONSOURCE:
      import fme
      import fmeobjects
      import math

      # 2015-12-28, Takashi Iijima: Original Implementation
      # 2015-12-29, Takashi Iijima: Added "Replace Segment between Spike Vertices with Vertex" option

      class ZigzagRemover(object):
          def __init__(self):
              self.GEOM_LINE = 1
              self.GEOM_POLYGON = 2
              self.GEOM_DONUT = 3
              self.LENGTH_LONGER = 10
              self.LENGTH_SHORTER = 11
              self.LENGTH_AVERAGE = 12
              self.SPIKE_CREATE_NONE = 20
              self.SPIKE_CREATE_POINT = 21
              self.SPIKE_CREATE_LINE = 22
              self.ATTR_REJECTED_REASON = '_rejected_reason'
              self.ATTR_RESULT_FLAG = '__zspikeremover.flag'

          def input(self, feature):
              try:
                  maxAngle = float(feature.getAttribute('__zspikeremover.maxangle'))
                  if maxAngle < 0 or 90 <= maxAngle:
                      raise Exception('Maximum Spike Angle should be 0 <= and < 90 degrees.')
                  self.maxAngleSine = math.sin(math.radians(maxAngle))
                  self.maxLength = feature.getAttribute('__zspikeremover.maxlength')
                  if self.maxLength:
                      self.maxLength = float(self.maxLength)
                      if self.maxLength <= 0.0:
                          raise Exception('Maximum Spike Length should be greater than 0 or <blank>.')
                  else:
                      self.maxLength = 0
                  self.funcSpikeLength = None
                  lenMode = feature.getAttribute('__zspikeremover.spike_length_is')
                  if lenMode.startswith('Longer'):
                      self.funcSpikeLength = lambda a, b: max(a, b)
                  elif lenMode.startswith('Shorter'):
                      self.funcSpikeLength = lambda a, b: min(a, b)
                  elif lenMode.startswith('Average'):
                      self.funcSpikeLength = lambda a, b: (a + b) * 0.5
                  else:
                      raise Exception('Debug: Undefined length comparison mode.')
                  self.spikeCreation = self.SPIKE_CREATE_NONE
                  spike_creation = feature.getAttribute('__zspikeremover.spike_creation')
                  if spike_creation.startswith('Point'):
                      self.spikeCreation = self.SPIKE_CREATE_POINT
                  elif spike_creation.startswith('Line'):
                      self.spikeCreation = self.SPIKE_CREATE_LINE
                  # 2015-12-29: Added this option.
                  self.replaceSegment = (feature.getAttribute('__zspikeremover.replace_segment') == 'Yes')
              except Exception as ex:
                  feature.setAttribute(self.ATTR_REJECTED_REASON, '%s' % ex)
                  feature.setAttribute(self.ATTR_RESULT_FLAG, 'terminate')
                  self.pyoutput(feature)
                  return

              # Get geometry type, create features list.
              # If the geometry is not supported, output the feature through the <Rejected> port.
              self.geomType = self.validateGeometry(feature)
              featureList = None
              if self.geomType in [self.GEOM_LINE, self.GEOM_POLYGON]:
                  featureList = [feature]
              elif self.geomType == self.GEOM_DONUT:
                  featureList = feature.getDonutParts()
              else:
                  feature.setAttribute(self.ATTR_RESULT_FLAG, 'rejected')
                  self.pyoutput(feature)
                  return

              # Remove spikes and duplicate vertices.
              coordsList, removed, numSpikes, duplicates = [], [], 0, []
              for part in featureList:
                  coords, spikes, scount, dup = self.removeSpikes(part.getAllCoordinates())
                  coordsList.append(coords)
                  removed += spikes
                  numSpikes += scount
                  duplicates += dup

              if 0 < numSpikes or 0 < len(duplicates):
                  # Update geometry of the input feature.
                  coords = coordsList[0]
                  isDegenerated = True
                  if self.geomType == self.GEOM_LINE:
                      if 1 < len(coords):
                          feature.setGeometry(fmeobjects.FMELine(coords))
                          isDegenerated = False
                  elif self.geomType == self.GEOM_POLYGON:
                      if 3 < len(coords):
                          feature.setGeometry(fmeobjects.FMEPolygon(fmeobjects.FMELine(coords)))
                          isDegenerated = False
                  elif self.geomType == self.GEOM_DONUT:
                      if 3 < len(coords):
                          outershell = feature.cloneAttributes()
                          outershell.setGeometry(fmeobjects.FMEPolygon(fmeobjects.FMELine(coords)))
                          partsList = [outershell]
                          count = 0 # counter of degenerated holes
                          for interior in coordsList[1:]:
                              if 3 < len(interior):
                                  hole = fmeobjects.FMEFeature()
                                  hole.setGeometry(fmeobjects.FMEPolygon(fmeobjects.FMELine(interior)))
                                  partsList.append(hole)
                              else:
                                  count += 1
                          feature.makeDonuts(partsList)
                          isDegenerated = (0 < count)
                  if isDegenerated:
                      if self.geomType == self.GEOM_DONUT and 3 < len(coords):
                          pass
                      elif 1 < len(coords):
                          feature.setGeometry(fmeobjects.FMELine(coords))
                      elif len(coords) == 1:
                          feature.setGeometry(fmeobjects.FMEPoint(*coords[0]))
                      else:
                          feature.removeGeometry()
                  feature.setAttribute(self.ATTR_RESULT_FLAG, 'changed' if not isDegenerated else 'degenerated')
                  feature.setAttribute('_num_spikes', numSpikes)
                  feature.setAttribute('_num_duplicates', len(duplicates))

                  # Output spikes (points or lines) and duplicate vertieces (points).
                  coordSys = feature.getCoordSys()
                  if self.spikeCreation != self.SPIKE_CREATE_NONE:
                      for coord, prop in removed:
                          spike = feature.cloneAttributes()
                          if self.spikeCreation == self.SPIKE_CREATE_POINT:
                              spike.setGeometry(fmeobjects.FMEPoint(*coord))
                          else:
                              spike.setGeometry(fmeobjects.FMELine(coord))
                          spike.setCoordSys(coordSys)
                          spike.setAttribute(self.ATTR_RESULT_FLAG, 'spike')
                          spike.setAttribute('_spike_angle', prop['angle'])
                          spike.setAttribute('_spike_length1', prop['length1'])
                          spike.setAttribute('_spike_length2', prop['length2'])
                          self.pyoutput(spike)
                  for coord in duplicates:
                      point = feature.cloneAttributes()
                      point.setGeometry(fmeobjects.FMEPoint(*coord))
                      point.setCoordSys(coordSys)
                      point.setAttribute(self.ATTR_RESULT_FLAG, 'duplicate')
                      self.pyoutput(point)

              # Output Unchanged or Changed feature.
              self.pyoutput(feature)

          # Returns supported geometry type code if supported, -1 otherwse.
          def validateGeometry(self, feature):
              geom = feature.getGeometry()
              if isinstance(geom, fmeobjects.FMECurve):
                  if geom.isLinear():
                      return self.GEOM_LINE
                  else:
                      feature.setAttribute(self.ATTR_REJECTED_REASON, 'non-linear curve is not supported')
                      return -1
              elif isinstance(geom, fmeobjects.FMEArea):
                  if geom.isBoundaryLinear():
                      return self.GEOM_DONUT if isinstance(geom, fmeobjects.FMEDonut) else self.GEOM_POLYGON
                  else:
                      feature.setAttribute(self.ATTR_REJECTED_REASON, 'non-linear boundary is not supported'),
                      return -1
              else:
                  feature.setAttribute(self.ATTR_REJECTED_REASON, 'unsupported geometry type')
                  return -1

          # Determines whether two segments form a spike and returns spike properties if the segments form a spike.
          # 2D Vector caltulation:
          # inner (dot) product = ax*bx + ay*by = |a|*|b|*cos(t)
          # outer (cross) product = ax*by - ay*bx = |a|*|b|*sin(t)
          # If the inner product of two vectors is less than 0, they form an acute angle.
          # Then, determine whether the absolute angle is less than the specified max spike angle.
          def getSpikeProperties(self, p0, p1, p2):
              ax, ay = p1[0] - p0[0], p1[1] - p0[1] # vector of the first segment
              bx, by = p2[0] - p1[0], p2[1] - p1[1] # vector of the second segment
              if ax * bx + ay * by < 0:
                  da, db = math.hypot(ax, ay), math.hypot(bx, by) # lengths of the segments
                  if self.maxLength == 0 or self.funcSpikeLength(da, db) <= self.maxLength:
                      sine = (ax * by - ay * bx) / (da * db)
                      if abs(sine) <= self.maxAngleSine:
                          return {'angle': math.degrees(math.asin(abs(sine))), 'length1': da, 'length2': db}
              return None

          def removeSpikes(self, srcCoords):
              # coords: List of a line or boundary coordinates tuples (x, y) or (x, y, z)
              # spikes: List of tuples (a spike coordinates or list of coordinates, dictionary of spike properties)
              # duplicates: List of removed duplicate coordinates tuples (x, y) or (x, y, z)
              coords, spikes, duplicates = [srcCoords[0]], [], []

              # Remove duplicate coordinates.
              for i in range(1, len(srcCoords)):
                  if srcCoords[i][0] == coords[-1][0] and srcCoords[i][1] == coords[-1][1]:
                      duplicates.append(srcCoords[i])
                  else:
                      coords.append(srcCoords[i])

              # Remove spikes.
              spikeProperties = {}
              if (2 if self.geomType == self.GEOM_LINE else 3) < len(coords):
                  for i in range(1, len(coords) - 1):
                      prop = self.getSpikeProperties(coords[i-1], coords[i], coords[i+1])
                      if prop:
                          spikeProperties[i] = prop
                  if self.geomType in [self.GEOM_POLYGON, self.GEOM_DONUT]:
                      prop = self.getSpikeProperties(coords[-2], coords[0], coords[1])
                      if prop:
                          spikeProperties[0] = spikeProperties[len(coords) - 1] = prop
                  if 0 < len(spikeProperties):
                      newCoords = []
                      for i, p in enumerate(coords):
                          if i not in spikeProperties:
                              newCoords.append(p)
                          elif i < len(coords) - 1:
                              if self.spikeCreation == self.SPIKE_CREATE_POINT:
                                  spikes.append((p, spikeProperties[i]))
                              elif self.spikeCreation == self.SPIKE_CREATE_LINE:
                                  prev = i - 1 if 0 < i else len(coords) - 2
                                  spikes.append(([coords[prev], p, coords[i+1]], spikeProperties[i]))
                              # 2015-12-29: Replace segment between 2 spike vertices with a vertex.
                              if self.replaceSegment and i + 1 in spikeProperties:
                                  newCoords.append(tuple([(a + b) * 0.5 for a, b in zip(p, coords[i+1])]))
                      if self.geomType in [self.GEOM_POLYGON, self.GEOM_DONUT] \
                          and 0 in spikeProperties and 2 < len(newCoords):
                          newCoords.append(newCoords[0]) # close coordinates of polygon boundary
                      coords = newCoords

              # Return coordinates, spikes, number of spikes, and dupulicate coordinates
              return coords, spikes, len(spikeProperties) - (1 if 0 in spikeProperties else 0), duplicates

          def close(self):
              pass
    PYTHONSYMBOL = ZigzagRemover
    -> AttributeFilter
AttributeFilter
    ATTR_NAME = __zspikeremover.flag
    ATTR_VALUES = <MISSING>,changed,degenerated,spike,duplicate,rejected,terminate,<EMPTY>,<NULL>,<UNFILTERED>
    <MISSING> -> Unchanged (output)
    changed -> Changed (output)
    degenerated -> Degenerated (output)
    spike -> Spike (output)
    duplicate -> Duplicate (output)
    rejected -> <Rejected> (output)
    terminate -> Terminator
Unchanged (output)
Changed (output)
Degenerated (output)
Spike (output)
Duplicate (output)
<Rejected> (output)
Terminator
    MESSAGE = @Value(_rejected_reason)

FME custom transformer NodeValence
Notes
    This transformer builds arc-node topology in attributes to mimic
    ARC/INFO
    Coverage network topology and adds 
    valence
    . See 
        topology_basics
    for some good diagrams and further discussion. After editing or filtering this process needs to be rerun, just like an
    ARC/INFO Build
    command to rebuild the correct relationships with new feature counts. The original system keys all ended in "#". The topology stack was stored as a series of layers inside a single dataset called a
    coverage
    .
    The lines have topology attributes exposed in the
    AAT
    table and nodes have attributes in the 
    NAT
    table, hence the suffix names 
    _aat
    and 
    _nat
    . The two featuretypes (lines and points) are intended to be considered as a single set. Not included in the
    AAT
    table is polygon topology which would contain the LPOLY# and RPOLY# identifiers.
    This process includes the equivalent of
    CLEAN
    which breaks all arcs at junctions, explodes all multiparts, removes all coincident lines and vertices.
    The addition of a 
    valence
    to the 
    NAT
    table is useful for analysis to classify
    dangles
    (1),
    pseudonodes
    (2),
    tees
    (3),
    intersections
    (4) or
    multiple junctions 
    (>4)
    .
    The arcs (lines) contain a foreign key to the 
    node_id
    in the 
    fnode
    and 
    tnode
    attributes to allow arcs to be tested for 
    direction 
    relative to the nodes.
    * Indexing the keys will be essential for reasonable performance when selecting or joining these two tables. Indexing in 
    ARC/INFO
    is implied because the original keys with a "#" in the name are the record number similiar to OBJECTID.
    * Tolerance defaults to 0.1 metre
    * The 
    arc_id
    is just one of the arcs joining the node as in the original model.
    * If arcs are not already split they will be split and therefore will duplicate existing attributes.
    * The fme_feature_ type is used to name the outputs the same as the source featuretype with a suffix _aat and _nat
Input is a branched polyline network <ft>
    Output is a cleaned line featuretype <ft>_aat and point representing nodes <ft>_nat
lines (PK arc_id) have fnode_id and tnode_id
nodes have node_id and valence and arc_id as first connecting arc
    Valence is a count of the number of arcs connecting at a node.

Note: Notes / This transformer builds arc-node topology in attributes to mimic ARC/INFO Coverage network topology and adds valence. See topology_basics for some good diagrams and further discussion. After editing or filtering this process needs to be rerun, just like an ARC/INFO Build command to rebuild the correct relationships with new feature counts. The original system keys all ended in "#". The topology stack was stored as a series of layers inside a single dataset called a coverage. / The lines have topology attributes exposed in the AAT table and nodes have attributes in the NAT table, hence the suffix names _aat and _nat. The two featuretypes (lines and points) are intended to be considered as a single set. Not included in the AAT table is polygon topology which would contain the LPOLY# and RPOLY# identifiers. / This process includes the equivalent of CLEAN which breaks all arcs at junctions, explodes all multiparts, removes all coincident lines and vertices. / The addition of a valence to the NAT table is useful for analysis to classify dangles (1), pseudonodes (2), tees (3), intersections (4) or multiple junctions (>4). / The arcs (lines) contain a foreign key to the node_id in the fnode and tnode attributes to allow arcs to be tested for direction relative to the nodes. / * Indexing the keys will be essential for reasonable performance when selecting or joining these two tables. Indexing in ARC/INFO is implied because the original keys with a "#" in the name are the record number similiar to OBJECTID. / * Tolerance defaults to 0.1 metre / * The arc_id is just one of the arcs joining the node as in the original model. / * If arcs are not already split they will be split and therefore will duplicate existing attributes. / * The fme_feature_ type is used to name the outputs the same as the source featuretype with a suffix _aat and _nat
Line (input)
    -> AttributeExposer

Bookmark: New Bookmark
Note: Splits arcs if not already split at intersections before assigning unique IDs which is transferred to the node. / Creates a point at every intersection and ends of every arc. Does not duplicate points at common junctions thank goodness / Adds a list of arcs connected to each node for the valence calculator
AttributeExposer
    ATTR_LIST = fme_feature_type
    -> First_Intersector
First_Intersector: Intersector
    DUPLICATE_Z_NODES = No
    LIST_NAME = all_reaches
    OV_ATTR = _overlaps
    PERFORM_SELF_INTERSECTION = No
    SEG_ATTR = _segments
    SEPARATE_COLLINEAR_SEGMENTS = No
    INTERSECTED -> arc_id_counter
arc_id_counter: Counter
    CNT_ATTR = arc_id
    DOMAIN = counter
    SCOPE = Local
    START = 1
    -> Intersector
Intersector
    DUPLICATE_Z_NODES = No
    LIST_NAME = all_reaches
    OV_ATTR = _overlaps
    PERFORM_SELF_INTERSECTION = No
    SEG_ATTR = _segments
    SEPARATE_COLLINEAR_SEGMENTS = No
    INTERSECTED -> Snipper_Begin
    INTERSECTED -> FeatureMerger_2 [REQUESTOR]
    NODE -> Node_id_counter

Bookmark: Distinguish between FNODE and TNODE (NeighborhoodPair does not)
Note: Snipper gets the first and last points. / Geohash is a spatial key to test for spatial coincidence with the nodes
Snipper_Begin
    ENDVERTEXATTR = 0
    SNIPMODE = Vertex
    STARTVERTEXATTR = 0
    -> Geohash_Begin
    REMNANTS -> Snipper_End
Geohash_Begin: GeometryExtractor
    ATTR = from_geohash
    GEOHASH_PRECISION_DISPLAY = ~9.3 mm (12 characters)
    KIND_LONG = Geohash
    -> FeatureMerger [REQUESTOR]
Snipper_End
    ENDVERTEXATTR = -1
    SNIPMODE = Vertex
    STARTVERTEXATTR = -1
    -> Geohash_End
Geohash_End: GeometryExtractor
    ATTR = to_geohash
    GEOHASH_PRECISION_DISPLAY = ~9.3 mm (12 characters)
    KIND_LONG = Geohash
    -> FeatureMerger_3 [REQUESTOR]
Geohash_node: GeometryExtractor
    ATTR = node_geohash
    GEOHASH_PRECISION_DISPLAY = ~9.3 mm (12 characters)
    KIND_LONG = Geohash
    -> FeatureMerger [SUPPLIER]
    -> FeatureMerger_3 [SUPPLIER]

Bookmark: Add node_id and valence
Node_id_counter: Counter
    CNT_ATTR = node_id
    DOMAIN = counter2
    SCOPE = Local
    START = 1
    -> ListElementCounter
Note: Valence
ListElementCounter
    CNT_ATTR = valence
    LIST_NAME = all_reaches{}
    -> AttributeKeeper
    -> Geohash_node
Note: Calculates the valence from the hidden list of arc-ids. / Output the nodes with unique ids. / arc_id is simply one of the connected arcs.
AttributeKeeper
    CREATE_BULK_MODE_FEATURES = No
    KEEP_ATTRS = arc_id,network_id,node_id,valence,fme_feature_type
    -> Node (output)

Bookmark: From Node
FeatureMerger
    ATTR_ACCUM_MODE = Merge Supplier
    ATTR_CONFLICT_RES = Use Requestor
    IGNORE_NULLS = No
    JOIN_KEYS = @Value(from_geohash) @Value(node_geohash) AUTO
    MERGE_TYPE = Attributes Only
    PROCESS_DUPS = No
    SUPPLIERS_FIRST = No
    MERGED -> AttributeCreator
Note: Join back the node_id as the from-node based on a Geohash match
AttributeCreator
    ATTR_LIST = fnode_id,@Value(node_id)
    -> AttributeKeeper_2
AttributeKeeper_2
    CREATE_BULK_MODE_FEATURES = No
    KEEP_ATTRS = arc_id,fnode_id
    -> FeatureMerger_2 [SUPPLIER]
FeatureMerger_2
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> FeatureMerger_4 [REQUESTOR]

Bookmark: To Node
FeatureMerger_3
    ATTR_ACCUM_MODE = Merge Supplier
    ATTR_CONFLICT_RES = Use Requestor
    IGNORE_NULLS = No
    JOIN_KEYS = @Value(to_geohash) @Value(node_geohash) AUTO
    MERGE_TYPE = Attributes Only
    PROCESS_DUPS = No
    SUPPLIERS_FIRST = No
    MERGED -> AttributeCreator_2
Note: Join back the node_id as the to-node based on a Geohash match
AttributeCreator_2
    ATTR_LIST = tnode_id,@Value(node_id)
    -> AttributeKeeper_3
AttributeKeeper_3
    CREATE_BULK_MODE_FEATURES = No
    KEEP_ATTRS = arc_id,tnode_id
    -> FeatureMerger_4 [SUPPLIER]
FeatureMerger_4
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> AttributeRemover

Bookmark: Tidy temp attributes
AttributeRemover
    LIST_ATTRS = all_reaches{} all_reaches{}.arc_id all_reaches{}.direction all_reaches{}.fme_basename all_reaches{}.ID all_reaches{}.name all_reaches{}.network_id all_reaches{}.OBJECTID all_reaches{}.SHAPE_Length
    REMOVE_ATTRS = _overlaps,_segments
    -> Arc (output)
Arc (output)

Bookmark: Write Nodes
Node (output)

FME custom transformer SequenceMatcher
SequenceMatcher
Campare the similarity of two string attribute values, and calcuates the ratio.
Category
Calculated Values
Input Ports
Input
Input features to append a ratio attribute
Parameters
AttributeA
AttributeA Contains a string value to compare to AttrbuteB's string value 
AttributeB
AttributeB Conatins the string value to match to AttributeA's string value
Output Ports
Output
Features are output with a new attribute containing a ratio attribute. The ratio lives in [0,1], where 0 means 0 % similarity and 1 is 100 % similar attribute values.

Parameters:
- AttributeA =   # AttributeA containing string value
- AttributeB =   # AttributeB containing string value

Input (input)
    -> ParameterFetcher
ParameterFetcher
    ATTR_LIST = _AttributeA $(AttributeA) _AttributeB $(AttributeB)
    -> PythonCaller
PythonCaller
    NEW_ATTRIBUTES = _ratio
    PYTHONSOURCE:
      from __future__ import print_function
      import fme
      import fmeobjects

      from difflib import SequenceMatcher

      def processFeature(feature):
          a = feature.getAttribute('_AttributeA')
          b = feature.getAttribute('_AttributeB')
          try:
              feature.setAttribute('_ratio', SequenceMatcher(None, a, b).ratio())
          except Exception as e:
              feature.setAttribute('_error', 'Invalid Parameters')
              feature.setAttribute('_pyError', str(e))
    PYTHONSYMBOL = processFeature
    -> Tester
Tester
    BOOL_OP = OR
    TEST_CLAUSE = TEST _ratio ATTRIBUTE_HAS_A_VALUE ""
    TEST_MODE = TEST
    PASSED -> Output (output)
    FAILED -> AttributeExposer
Output (output)
AttributeExposer
    ATTR_LIST = _error,_pyError
    -> <Rejected> (output)
<Rejected> (output)
