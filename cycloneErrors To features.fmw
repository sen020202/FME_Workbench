FME workspace cycloneErrors To features.fmw

Parameters:
- DestDataset_DGNV8 = D:\02_Pilot\Vienna subway\Delivery\vsen delivery\UG\frommarik_OUTPUT.dgn   # Destination Bentley MicroStation Design File
- SourceDataset_DGNV8XFM = D:\02_Pilot\Vienna subway\Delivery\vsen delivery\UG\frommarik.dgn   # Source Bentley MicroStation Design File(s)
- FEATURE_TYPES = Default

Readers:
- DGNV8XFM_1: DGNV8XFM from $(SourceDataset_DGNV8XFM)

Writers:
- DGNV8_1: DGNV8 to $(DestDataset_DGNV8)

Default (reader DGNV8XFM_1)
    -> CoordinateExtractor
CoordinateExtractor
    LIST_NAME = _indices
    MODE = All Coordinates
    -> VertexCreator
VertexCreator
    CLOSE_LINES = Yes
    IGNORE_DUPLICATES = No
    MEASURE_TYPE = Continuous
    MISSING_VAL_MODE = Compute
    MODE_NAME = Add Point
    XVAL = @Value(_indices{0}.x)
    YVAL = @Value(_indices{0}.y)
    ZVAL = @Value(_indices{0}.z)
    -> TestFilter
    -> TestFilter_2
    -> TestFilter_3
    -> TestFilter_4
    -> TestFilter_5
    -> TestFilter_6
TestFilter
    DEFAULT_VALUE = <UNFILTERED>
    PASSED_TEST_GROUP_OUTPUT = FIRST
    TEST_LIST:
      "BOOL_OP,OR,COMPOSITE_TEST,""""""1 OR 2"""""",TEST_CLAUSE,CASE_INSENSITIVE_TEST @Value(igds_text_string) ENDS_WITH Switch
      CASE_INSENSITIVE_TEST @Value(igds_text_string) ENDS_WITH switch",@Value(igds_text_string) ENDS_WITH Switch
    <UNFILTERED> -> AttributeCreator
AttributeCreator
    ATTR_TABLE = SET_TO igds_level_name (buffer) = Switch
    -> 0 (writer DGNV8_1)
TestFilter_2
    DEFAULT_VALUE = <UNFILTERED>
    PASSED_TEST_GROUP_OUTPUT = FIRST
    TEST_LIST:
      "BOOL_OP,OR,COMPOSITE_TEST,""""""1 OR 2"""""",TEST_CLAUSE,CASE_INSENSITIVE_TEST @Value(igds_text_string) ENDS_WITH Box
      CASE_INSENSITIVE_TEST @Value(igds_text_string) ENDS_WITH box",@Value(igds_text_string) ENDS_WITH Switch
    @Value(igds_text_string) ENDS_WITH Switch -> AttributeCreator_2
AttributeCreator_2
    ATTR_TABLE = SET_TO igds_level_name (buffer) = Distribution_Box
    -> 0 (writer DGNV8_1)
TestFilter_3
    DEFAULT_VALUE = <UNFILTERED>
    PASSED_TEST_GROUP_OUTPUT = FIRST
    TEST_LIST:
      "BOOL_OP,OR,COMPOSITE_TEST,""""""1 OR 2 OR 3"""""",TEST_CLAUSE,CASE_INSENSITIVE_TEST @Value(igds_text_string) ENDS_WITH Plugs
      CASE_INSENSITIVE_TEST @Value(igds_text_string) ENDS_WITH plug
      CASE_INSENSITIVE_TEST @Value(igds_text_string) ENDS_WITH plugs",@Value(igds_text_string) ENDS_WITH Switch
    @Value(igds_text_string) ENDS_WITH Switch -> AttributeCreator_3
AttributeCreator_3
    ATTR_TABLE = SET_TO igds_level_name (buffer) = Plugs
    -> 0 (writer DGNV8_1)
TestFilter_4
    DEFAULT_VALUE = <UNFILTERED>
    PASSED_TEST_GROUP_OUTPUT = FIRST
    TEST_LIST:
      "BOOL_OP,OR,COMPOSITE_TEST,""""""1 OR 2 OR 3"""""",TEST_CLAUSE,CASE_INSENSITIVE_TEST @Value(igds_text_string) ENDS_WITH Light
      CASE_INSENSITIVE_TEST @Value(igds_text_string) ENDS_WITH Lights
      CASE_INSENSITIVE_TEST @Value(igds_text_string) ENDS_WITH lights",@Value(igds_text_string) ENDS_WITH Switch
    @Value(igds_text_string) ENDS_WITH Switch -> AttributeCreator_4
AttributeCreator_4
    ATTR_TABLE = SET_TO igds_level_name (buffer) = Lights
    -> 0 (writer DGNV8_1)
TestFilter_5
    DEFAULT_VALUE = <UNFILTERED>
    PASSED_TEST_GROUP_OUTPUT = FIRST
    TEST_LIST:
      "BOOL_OP,OR,COMPOSITE_TEST,""""""1 OR 2 OR 3"""""",TEST_CLAUSE,CASE_INSENSITIVE_TEST @Value(igds_text_string) CONTAINS Eme
      CASE_INSENSITIVE_TEST @Value(igds_text_string) CONTAINS Emergency
      CASE_INSENSITIVE_TEST @Value(igds_text_string) CONTAINS emergency",@Value(igds_text_string) ENDS_WITH Switch
    @Value(igds_text_string) ENDS_WITH Switch -> AttributeCreator_5
AttributeCreator_5
    ATTR_TABLE = SET_TO igds_level_name (buffer) = Emergency_Station
    -> 0 (writer DGNV8_1)
TestFilter_6
    DEFAULT_VALUE = <UNFILTERED>
    PASSED_TEST_GROUP_OUTPUT = FIRST
    TEST_LIST:
      "BOOL_OP,OR,COMPOSITE_TEST,""""""1 OR 2 OR 3"""""",TEST_CLAUSE,CASE_INSENSITIVE_TEST @Value(igds_text_string) CONTAINS door
      CASE_INSENSITIVE_TEST @Value(igds_text_string) CONTAINS Door
      CASE_INSENSITIVE_TEST @Value(igds_text_string) CONTAINS doors",@Value(igds_text_string) ENDS_WITH Switch
    @Value(igds_text_string) ENDS_WITH Switch -> AttributeCreator_6
AttributeCreator_6
    ATTR_TABLE = SET_TO igds_level_name (buffer) = Door
    -> 0 (writer DGNV8_1)
0 (writer DGNV8_1)
    attributes: _indices{}.x double, _indices{}.y double, _indices{}.z double
