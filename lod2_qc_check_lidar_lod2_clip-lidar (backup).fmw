FME workspace lod2_qc_check_lidar_lod2_clip-lidar (backup).fmw
Title: Check LOD2 output

Parameters:
- buffer_rp_edge = -0.20   # Buffer roof part edge
- Min_diff_marker_m = 0.2   # Minimum height difference to see as error
- GBG_GEOJSON = O:\Data5\0-PRODUCTS\11-LOD2\Laakdal\Laakdal_gbg.geojson   # GBG geojson
- LOD2_DGN_file = O:\Data5\0-PRODUCTS\11-LOD2\Laakdal\LOD2 Laakdal 2022.dgn   # LOD2 DGN file
- POINT_CLOUD_LAS = O:\Data5\0-PRODUCTS\9-LIDAR\1-VLAANDEREN\Laakdal\22_06_Laakdal\*_Laakdal.laz   # LAS/LAZ files Point Clouds
- OUTPUT_GEOM_ISSUES_ROOFS = O:\Data5\0-PRODUCTS\11-LOD2\Laakdal\qc\LOD2 Laakdal 2022 geom-issues-roofs.gpkg   # Output Geom issues roofs [GPKG]
- OUTPUT_GEOM_ISSUES_FOOTPRINTS = O:\Data5\0-PRODUCTS\11-LOD2\Laakdal\qc\LOD2 Laakdal 2022 geom-issues-footprints.gpkg   # Output Geom issues footprints [GPKG]
- OUTPUT_ROOF_DIFFERENCES = O:\Data5\0-PRODUCTS\11-LOD2\Laakdal\qc\LOD2 Laakdal 2022 roof-errors.gpkg   # Output LOD2 check with LiDAR [GPKG]
- OUTPUT_MISSING_ROOFS = O:\Data5\0-PRODUCTS\11-LOD2\Laakdal\qc\LOD2 Laakdal 2022 missing-roofs.gpkg   # Output missing roofs [GPKG]
- OUTPUT_ROOFS_WITH_DIFFERENCES_GEOJSON = O:\Data5\0-PRODUCTS\11-LOD2\Oosterzele\21-Dec-2022\LOD2 Oosterzele 2022 roofs.geojson   # Output roofs with errors [GeoJSON]
- OUTPUT_ROOFS_WITH_DIFFERENCES_GPKG = O:\Data5\0-PRODUCTS\11-LOD2\Oosterzele\21-Dec-2022\LOD2 Oosterzele 2022 roofs.gpkg   # Output roofs with errors [GPKG]

Readers:
- IGDS_1: IGDS from $(LOD2_DGN_file) in EPSG:31370
- LAS_1: LAS from $(POINT_CLOUD_LAS)
- GEOJSON_3: GEOJSON from $(GBG_GEOJSON) in EPSG:31370

Writers:
- OGCGEOPACKAGE_1: OGCGEOPACKAGE to $(OUTPUT_GEOM_ISSUES_ROOFS) in EPSG:31370
- OGCGEOPACKAGE_3: OGCGEOPACKAGE to $(OUTPUT_GEOM_ISSUES_FOOTPRINTS) in EPSG:31370
- OGCGEOPACKAGE_4: OGCGEOPACKAGE to $(OUTPUT_ROOFS_WITH_DIFFERENCES_GPKG) in EPSG:31370
- GEOJSON_1: GEOJSON to $(OUTPUT_ROOFS_WITH_DIFFERENCES_GEOJSON) in EPSG:31370
- OGCGEOPACKAGE_5: OGCGEOPACKAGE to $(OUTPUT_ROOF_DIFFERENCES)
- OGCGEOPACKAGE_2: OGCGEOPACKAGE to $(OUTPUT_MISSING_ROOFS) in EPSG:31370

Tessenderlo_gbg (reader GEOJSON_3)
    attributes: id string, OIDN int, TYPE int
    -> ClipperMissingRoofs [CANDIDATE]
LAS (reader LAS_1)
    -> ClipperPointCloudGBG [CANDIDATE]
Note: Roofs DGN
5 (reader IGDS_1)
    -> FeatureMerger [REQUESTOR]
    -> Triangulator
    -> GeometryValidatorRoof
    -> FeatureMergerInvalidCroppedRoofParts [REQUESTOR]
    -> ClipperDSMs [CLIPPER]
    -> ClipperPointCloudGBG [CLIPPER]
    -> BuffererInside
    -> ClipperMissingRoofs [CLIPPER]
ClipperPointCloudGBG
    BOUNDARY_CASES = OUTSIDE
    CLEANING_TOLERANCE = Automatic
    CLIPPERS_FIRST = NO
    GENERATE_LIST = NO
    INVALID_PARTS_HANDLING = REJECT_PARTS
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterDEMGenerator [POINTS/LINES]
RasterDEMGenerator
    INTERPOLATION_TYPE = PLANAR
    NODATA_VALUE = 0
    TOLERANCE = 0.25
    X_SPACING = 0.25
    Y_SPACING = 0.25
    DEM_RASTER -> RasterBandNodataSetter
RasterBandNodataSetter
    NODATA_VALUE = 0
    REPLACE_CELL_VALUES = No
    -> PointOnRasterValueExtractor [RASTER]
PointOnRasterValueExtractor
    INTERPOLATION_TYPE_NAME = Bicubic
    POINT -> AttributeCreatorLod2
AttributeCreatorLod2
    ATTR_TABLE:
      SET_TO z_lidar = @Value(_band{0}.value)
      SET_TO z_diff = @abs(@sub(@Value(z_lidar),@Value(z_lod2)))
    -> TestFilterDSM
TestFilterDSM
    DEFAULT_VALUE = <UNFILTERED>
    PASSED_TEST_GROUP_OUTPUT = FIRST
    TEST_LIST = "BOOL_OP,OR,COMPOSITE_TEST,""""""1"""""",TEST_CLAUSE,TEST @Value(z_lidar) > 0",dsm_px_found
    dsm_px_found -> AttributeManager
AttributeManager
    ATTR_TABLE:
      REMOVE _band{}.value
      REMOVE _band{}.palette{}.value
    USER_EXPOSED_ATTRIBUTES = z_lidar
    -> TestFilterErrorAboveMargin
TestFilterErrorAboveMargin
    DEFAULT_VALUE = good
    PASSED_TEST_GROUP_OUTPUT = FIRST
    TEST_LIST = "BOOL_OP,OR,COMPOSITE_TEST,""""""1"""""",TEST_CLAUSE,TEST @Value(z_diff) >= $(Min_diff_marker_m)",errors
    errors -> Aggregator
    errors -> 2DForcer
Aggregator
    ACCUM_ATTRS_NAME = Drop Incoming Attributes
    AGGREGATE_TYPE = Homogeneous Collection (If Possible)
    GROUP_BY = igds_element_id
    MODE = Geometry - Assemble One Level
    SEP = ,
    SUM = z_diff
    AGGREGATE -> FeatureMerger [SUPPLIER]
error areas (writer OGCGEOPACKAGE_5)
    attributes: z_lidar double, z_diff double, igds_element_id mediumint, z_lod2 double
Note: Footprints DGN
7 (reader IGDS_1)
    -> GeometryValidatorFootprint

Bookmark: 3D polygons to PC
Triangulator
    DEAGGREGATE_INPUT = Deaggregate
    TIN_SURFACE -> PointCloudCombiner
PointCloudCombiner
    ACCUM_ATTRS_NAME = Yes
    EXTRACT_RASTER_NODATA_NAME = No
    GROUP_BY = igds_element_id
    SPACING = 0.5
    -> ClipperDSMs [CANDIDATE]
ClipperDSMs
    ATTR_ACCUM_MODE = MERGE
    ATTR_CONFLICT_RES = CANDIDATE
    BOUNDARY_CASES = INSIDE
    CLEANING_TOLERANCE = Automatic
    CLIPPERS_FIRST = NO
    GENERATE_LIST = NO
    GROUP_BY = igds_element_id
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = BOUNDARY
    Z_VAL_SOURCE = CANDIDATE
    INSIDE -> PointCloudToPointCoercerLod2DSM
PointCloudToPointCoercerLod2DSM
    ACCUM_ATTRS_NAME = Yes
    CONVERT_TO_DISPLAY = Individual Points
    POINT_COMPONENTS_PRESERVE_DISPLAY = Attributes
    COERCED -> CoordinateExtractor
CoordinateExtractor
    IND = 0
    MODE = Specify Coordinate
    Z_ATTR = z_lod2
    -> PointOnRasterValueExtractor [POINT]

Bookmark: Output roof parts where an error point is found
FeatureMerger [off]
    ATTR_ACCUM_MODE = Merge Supplier
    ATTR_CONFLICT_RES = Use Requestor
    GROUP_BY = igds_element_id
    IGNORE_NULLS = No
    JOIN_KEYS = @Value(igds_element_id) @Value(igds_element_id) AUTO
    MERGE_TYPE = Attributes Only
    PROCESS_DUPS = NO
    REJECT_NULL_MISSING_KEYS = No
    SUPPLIERS_FIRST = No
    MERGED -> AreaCalculator
AreaCalculator [off]
    AREA_ATTR = area
    AREA_TYPE = Sloped Area
    MULT = 1
    -> AttributeCreatorRoofPart
AttributeCreatorRoofPart [off]
    ATTR_TABLE = SET_TO err_on_area = @div(@Value(z_diff),@Value(area))
    -> Roof issues (writer GEOJSON_1)
    -> Roof issues (writer OGCGEOPACKAGE_4)
Note: 5: LOD2 Oosterzele 2022 roofs [GEOJSON]
Roof issues (writer GEOJSON_1) [off]
    attributes: err_on_area string, igds_element_id int, z_diff string, area float
Note: 5: LOD2 Oosterzele 2022 roofs [OGCGEOPACKAGE]
Roof issues (writer OGCGEOPACKAGE_4) [off]
    attributes: err_on_area text(200), igds_element_id mediumint, z_diff text(200), area double

Bookmark: Filter error regions (Remove at edge of polygons)
2DForcer
    2D -> Bufferer
Bufferer
    ANGLE = 22.5
    CAP_STYLE = Square
    CORNER_STYLE = Bevel
    MODE = AREA
    OFFSET = 0.26
    OFFSET_UNITS = NONE
    PRECISION = APPROX
    BUFFERED -> SpatialFilter [Candidate]
GeometryCoercer
    GQUERY:
      for $geom in //geometry
      where $geom/count(parent::geometry) = 0
      return number($geom/@fme_id)
    KIND = fme_line
    COERCED -> SpatialFilter [Filter]
SpatialFilter
    AGGREGATE_HANDLING = Yes
    BASE_TYPE = Multiple Filters
    CURVE_BOUNDARY_RULE_PARAM = Default Rule
    PASS_CRITERIA = Pass Against One Filter
    PREDATTR = _predicate
    PREDICATES = DISJOINT WITHIN CONTAINS EQUALS
    USE_BOUNDING_BOX = No
    PASSED -> error areas (writer OGCGEOPACKAGE_5)

Bookmark: Buffer roof parts to the inside
BuffererInside
    ANGLE = 22.5
    CAP_STYLE = Square
    CORNER_STYLE = Bevel
    MODE = AREA
    OFFSET = $(buffer_rp_edge)
    OFFSET_UNITS = METERS
    PRECISION = APPROX
    BUFFERED -> GeometryValidatorCroppedRoofPart
GeometryValidatorCroppedRoofPart
    ISSUE_ATTR_NAME = _issues
    PRESETS = Custom
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_CHECK_AREA]TOLERANCE_MODE]IGNORE]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]Yes]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> GeometryCoercer
    FAILED -> FeatureMergerInvalidCroppedRoofParts [SUPPLIER]
    REPAIRED -> GeometryCoercer
FeatureMergerInvalidCroppedRoofParts
    ATTR_ACCUM_MODE = Merge Supplier
    ATTR_CONFLICT_RES = Use Requestor
    GROUP_BY = igds_element_id
    IGNORE_NULLS = No
    JOIN_KEYS = @Value(igds_element_id) @Value(igds_element_id) AUTO
    MERGE_TYPE = Attributes Only
    PROCESS_DUPS = NO
    REJECT_NULL_MISSING_KEYS = No
    SUPPLIERS_FIRST = No
    MERGED -> GeometryCoercer

Bookmark: Invalid geometries
GeometryValidatorRoof
    ISSUE_ATTR_NAME = issues
    PRESETS = Custom
    REPAIR = Yes
    RULES = SELF_INTERSECTING CHECK_HOLE_TOUCHING_POLYGON]Yes]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING
    SUMMARY = Detailed
    FAILED -> CenterPointReplacerInvalidRoof
CenterPointReplacerInvalidRoof
    POINTTYPE = CENTEROFGRAV
    POINT -> Invalid roof geometries (writer OGCGEOPACKAGE_1)
Invalid roof geometries (writer OGCGEOPACKAGE_1)
    attributes: igds_element_id mediumint, issues{}.count int, issues{}.issue_found text, issues{}.location_sample.x double, issues{}.location_sample.y double, issues{}.location_sample.z double, issues{}.repair_state text
GeometryValidatorFootprint
    ISSUE_ATTR_NAME = issues
    PRESETS = Custom
    REPAIR = Yes
    RULES = SELF_INTERSECTING CHECK_HOLE_TOUCHING_POLYGON]Yes]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING
    SUMMARY = Detailed
    FAILED -> CenterPointReplacerInvalidFootprint
CenterPointReplacerInvalidFootprint
    POINTTYPE = CENTEROFGRAV
    POINT -> Invalid footprint geometries (writer OGCGEOPACKAGE_3)
Invalid footprint geometries (writer OGCGEOPACKAGE_3)
    attributes: igds_element_id mediumint, issues{}.count int, issues{}.issue_found text, issues{}.location_sample.x double, issues{}.location_sample.y double, issues{}.location_sample.z double, issues{}.repair_state text

Bookmark: Missing roof parts
ClipperMissingRoofs
    BOUNDARY_CASES = OUTSIDE
    CLEANING_TOLERANCE = 0
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> GeometryFilter
    REMNANTS -> GeometryFilter
GeometryFilter
    FILTER_MODE = SIMPLE
    FILTER_MULTI = FILTER_TYPES]Area]FME_CONTROLLER_QUERY_FILE]]FME_CONTROLLER_CHOICE]Simple
    Area -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculatorMissingPart
Missing roof parts (writer OGCGEOPACKAGE_2)
    attributes: id text, OIDN int, TYPE int, _part_number text(20), _geometry_name text, area double

Bookmark: Filter area >= 1.9m²
AreaCalculatorMissingPart
    AREA_ATTR = area
    AREA_TYPE = Sloped Area
    MULT = 1
    -> TesterLargeArea
TesterLargeArea
    BOOL_OP = OR
    TEST_CLAUSE = TEST @Value(area) >= 1.9
    TEST_MODE = TEST
    PASSED -> Missing roof parts (writer OGCGEOPACKAGE_2)
