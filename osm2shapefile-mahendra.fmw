FME workspace osm2shapefile-mahendra.fmw

Parameters:
- DestDataset_SHAPEFILE =
- SourceDataset_OSM =

Readers:
- OSM_1: OSM from $(SourceDataset_OSM)

Writers:
- SHAPEFILE_1: SHAPEFILE to $(DestDataset_SHAPEFILE)

GeometryFilter
    BREAK_AGG = Yes
    GEOM_PORT_NAMES = Point Line Area Collection Null
    INSTANTIATE = Yes
    POINT -> aerialway_point (writer SHAPEFILE_1)
    LINE -> aerialway_line (writer SHAPEFILE_1)
    AREA -> aerialway_polygon (writer SHAPEFILE_1)
    COLLECTION -> aerialway_geom (writer SHAPEFILE_1)
    NULL -> aerialway_geom (writer SHAPEFILE_1)
GeometryFilter_2
    BREAK_AGG = Yes
    GEOM_PORT_NAMES = Point Line Area Collection Null
    INSTANTIATE = Yes
    POINT -> aeroway_point (writer SHAPEFILE_1)
    LINE -> aeroway_line (writer SHAPEFILE_1)
    AREA -> aeroway_polygon (writer SHAPEFILE_1)
    COLLECTION -> aeroway_geom (writer SHAPEFILE_1)
    NULL -> aeroway_geom (writer SHAPEFILE_1)
GeometryFilter_28
    BREAK_AGG = Yes
    GEOM_PORT_NAMES = Point Line Area Collection Null
    INSTANTIATE = Yes
    POINT -> waterway_point (writer SHAPEFILE_1)
    LINE -> waterway_line (writer SHAPEFILE_1)
    AREA -> waterway_polygon (writer SHAPEFILE_1)
    COLLECTION -> waterway_geom (writer SHAPEFILE_1)
    NULL -> waterway_geom (writer SHAPEFILE_1)
GeometryFilter_4
    BREAK_AGG = Yes
    GEOM_PORT_NAMES = Point Line Area Collection Null
    INSTANTIATE = Yes
    POINT -> barrier_point (writer SHAPEFILE_1)
    LINE -> barrier_line (writer SHAPEFILE_1)
    AREA -> barrier_polygon (writer SHAPEFILE_1)
    COLLECTION -> barrier_geom (writer SHAPEFILE_1)
    NULL -> barrier_geom (writer SHAPEFILE_1)
GeometryFilter_3
    BREAK_AGG = Yes
    GEOM_PORT_NAMES = Point Line Area Collection Null
    INSTANTIATE = Yes
    POINT -> amenity_point (writer SHAPEFILE_1)
    LINE -> amenity_line (writer SHAPEFILE_1)
    AREA -> amenity_polygon (writer SHAPEFILE_1)
    COLLECTION -> amenity_geom (writer SHAPEFILE_1)
    NULL -> amenity_geom (writer SHAPEFILE_1)
GeometryFilter_9
    BREAK_AGG = Yes
    GEOM_PORT_NAMES = Point Line Area Collection Null
    INSTANTIATE = Yes
    POINT -> geological_point (writer SHAPEFILE_1)
    LINE -> geological_line (writer SHAPEFILE_1)
    AREA -> geological_polygon (writer SHAPEFILE_1)
    COLLECTION -> geological_geom (writer SHAPEFILE_1)
    NULL -> geological_geom (writer SHAPEFILE_1)
GeometryFilter_17
    BREAK_AGG = Yes
    GEOM_PORT_NAMES = Point Line Area Collection Null
    INSTANTIATE = Yes
    POINT -> office_point (writer SHAPEFILE_1)
    LINE -> office_line (writer SHAPEFILE_1)
    AREA -> office_polygon (writer SHAPEFILE_1)
    COLLECTION -> office_geom (writer SHAPEFILE_1)
    NULL -> office_geom (writer SHAPEFILE_1)
GeometryFilter_5
    BREAK_AGG = Yes
    GEOM_PORT_NAMES = Point Line Area Collection Null
    INSTANTIATE = Yes
    POINT -> boundary_point (writer SHAPEFILE_1)
    LINE -> boundary_line (writer SHAPEFILE_1)
    AREA -> boundary_polygon (writer SHAPEFILE_1)
    COLLECTION -> boundary_geom (writer SHAPEFILE_1)
    NULL -> boundary_geom (writer SHAPEFILE_1)
GeometryFilter_6
    BREAK_AGG = Yes
    GEOM_PORT_NAMES = Point Line Area Collection Null
    INSTANTIATE = Yes
    POINT -> building_point (writer SHAPEFILE_1)
    LINE -> building_line (writer SHAPEFILE_1)
    AREA -> building_polygon (writer SHAPEFILE_1)
    COLLECTION -> building_geom (writer SHAPEFILE_1)
    NULL -> building_geom (writer SHAPEFILE_1)
GeometryFilter_7
    BREAK_AGG = Yes
    GEOM_PORT_NAMES = Point Line Area Collection Null
    INSTANTIATE = Yes
    POINT -> craft_point (writer SHAPEFILE_1)
    LINE -> craft_line (writer SHAPEFILE_1)
    AREA -> craft_polygon (writer SHAPEFILE_1)
    COLLECTION -> craft_geom (writer SHAPEFILE_1)
    NULL -> craft_geom (writer SHAPEFILE_1)
GeometryFilter_8
    BREAK_AGG = Yes
    GEOM_PORT_NAMES = Point Line Area Collection Null
    INSTANTIATE = Yes
    POINT -> emergency_point (writer SHAPEFILE_1)
    LINE -> emergency_line (writer SHAPEFILE_1)
    AREA -> emergency_polygon (writer SHAPEFILE_1)
    COLLECTION -> emergency_geom (writer SHAPEFILE_1)
    NULL -> emergency_geom (writer SHAPEFILE_1)
GeometryFilter_18
    BREAK_AGG = Yes
    GEOM_PORT_NAMES = Point Line Area Collection Null
    INSTANTIATE = Yes
    POINT -> place_point (writer SHAPEFILE_1)
    LINE -> place_line (writer SHAPEFILE_1)
    AREA -> place_polygon (writer SHAPEFILE_1)
    COLLECTION -> place_geom (writer SHAPEFILE_1)
    NULL -> place_geom (writer SHAPEFILE_1)
GeometryFilter_10
    BREAK_AGG = Yes
    GEOM_PORT_NAMES = Point Line Area Collection Null
    INSTANTIATE = Yes
    POINT -> highway_point (writer SHAPEFILE_1)
    LINE -> highway_line (writer SHAPEFILE_1)
    AREA -> highway_polygon (writer SHAPEFILE_1)
    COLLECTION -> highway_geom (writer SHAPEFILE_1)
    NULL -> highway_geom (writer SHAPEFILE_1)
GeometryFilter_11
    BREAK_AGG = Yes
    GEOM_PORT_NAMES = Point Line Area Collection Null
    INSTANTIATE = Yes
    POINT -> historic_point (writer SHAPEFILE_1)
    LINE -> historic_line (writer SHAPEFILE_1)
    AREA -> historic_polygon (writer SHAPEFILE_1)
    COLLECTION -> historic_geom (writer SHAPEFILE_1)
    NULL -> historic_geom (writer SHAPEFILE_1)
GeometryFilter_13
    BREAK_AGG = Yes
    GEOM_PORT_NAMES = Point Line Area Collection Null
    INSTANTIATE = Yes
    POINT -> leisure_point (writer SHAPEFILE_1)
    LINE -> leisure_line (writer SHAPEFILE_1)
    AREA -> leisure_polygon (writer SHAPEFILE_1)
    COLLECTION -> leisure_geom (writer SHAPEFILE_1)
    NULL -> leisure_geom (writer SHAPEFILE_1)
GeometryFilter_12
    BREAK_AGG = Yes
    GEOM_PORT_NAMES = Point Line Area Collection Null
    INSTANTIATE = Yes
    POINT -> landuse_point (writer SHAPEFILE_1)
    LINE -> landuse_line (writer SHAPEFILE_1)
    AREA -> landuse_polygon (writer SHAPEFILE_1)
    COLLECTION -> landuse_geom (writer SHAPEFILE_1)
    NULL -> landuse_geom (writer SHAPEFILE_1)
GeometryFilter_26
    BREAK_AGG = Yes
    GEOM_PORT_NAMES = Point Line Area Collection Null
    INSTANTIATE = Yes
    POINT -> unfiltered_point (writer SHAPEFILE_1)
    LINE -> unfiltered_line (writer SHAPEFILE_1)
    AREA -> unfiltered_polygon (writer SHAPEFILE_1)
    COLLECTION -> unfiltered_geom (writer SHAPEFILE_1)
    NULL -> unfiltered_geom (writer SHAPEFILE_1)
GeometryFilter_14
    BREAK_AGG = Yes
    GEOM_PORT_NAMES = Point Line Area Collection Null
    INSTANTIATE = Yes
    POINT -> man_made_point (writer SHAPEFILE_1)
    LINE -> man_made_line (writer SHAPEFILE_1)
    AREA -> man_made_polygon (writer SHAPEFILE_1)
    COLLECTION -> man_made_geom (writer SHAPEFILE_1)
    NULL -> man_made_geom (writer SHAPEFILE_1)
GeometryFilter_16
    BREAK_AGG = Yes
    GEOM_PORT_NAMES = Point Line Area Collection Null
    INSTANTIATE = Yes
    POINT -> natural_point (writer SHAPEFILE_1)
    LINE -> natural_line (writer SHAPEFILE_1)
    AREA -> natural_polygon (writer SHAPEFILE_1)
    COLLECTION -> natural_geom (writer SHAPEFILE_1)
    NULL -> natural_geom (writer SHAPEFILE_1)
GeometryFilter_15
    BREAK_AGG = Yes
    GEOM_PORT_NAMES = Point Line Area Collection Null
    INSTANTIATE = Yes
    POINT -> military_point (writer SHAPEFILE_1)
    LINE -> military_line (writer SHAPEFILE_1)
    AREA -> military_polygon (writer SHAPEFILE_1)
    COLLECTION -> military_geom (writer SHAPEFILE_1)
    NULL -> military_geom (writer SHAPEFILE_1)
GeometryFilter_20
    BREAK_AGG = Yes
    GEOM_PORT_NAMES = Point Line Area Collection Null
    INSTANTIATE = Yes
    POINT -> public_transport_point (writer SHAPEFILE_1)
    LINE -> public_transport_line (writer SHAPEFILE_1)
    AREA -> public_transport_polygon (writer SHAPEFILE_1)
    COLLECTION -> public_transport_geom (writer SHAPEFILE_1)
    NULL -> public_transport_geom (writer SHAPEFILE_1)
GeometryFilter_24
    BREAK_AGG = Yes
    GEOM_PORT_NAMES = Point Line Area Collection Null
    INSTANTIATE = Yes
    POINT -> sport_point (writer SHAPEFILE_1)
    LINE -> sport_line (writer SHAPEFILE_1)
    AREA -> sport_polygon (writer SHAPEFILE_1)
    COLLECTION -> sport_geom (writer SHAPEFILE_1)
    NULL -> sport_geom (writer SHAPEFILE_1)
GeometryFilter_19
    BREAK_AGG = Yes
    GEOM_PORT_NAMES = Point Line Area Collection Null
    INSTANTIATE = Yes
    POINT -> power_point (writer SHAPEFILE_1)
    LINE -> power_line (writer SHAPEFILE_1)
    AREA -> power_polygon (writer SHAPEFILE_1)
    COLLECTION -> power_geom (writer SHAPEFILE_1)
    NULL -> power_geom (writer SHAPEFILE_1)
GeometryFilter_21
    BREAK_AGG = Yes
    GEOM_PORT_NAMES = Point Line Area Collection Null
    INSTANTIATE = Yes
    POINT -> railway_point (writer SHAPEFILE_1)
    LINE -> railway_line (writer SHAPEFILE_1)
    AREA -> railway_polygon (writer SHAPEFILE_1)
    COLLECTION -> railway_geom (writer SHAPEFILE_1)
    NULL -> railway_geom (writer SHAPEFILE_1)
GeometryFilter_22
    BREAK_AGG = Yes
    GEOM_PORT_NAMES = Point Line Area Collection Null
    INSTANTIATE = Yes
    POINT -> route_point (writer SHAPEFILE_1)
    LINE -> route_line (writer SHAPEFILE_1)
    AREA -> route_polygon (writer SHAPEFILE_1)
    COLLECTION -> route_geom (writer SHAPEFILE_1)
    NULL -> route_geom (writer SHAPEFILE_1)
GeometryFilter_23
    BREAK_AGG = Yes
    GEOM_PORT_NAMES = Point Line Area Collection Null
    INSTANTIATE = Yes
    POINT -> shop_point (writer SHAPEFILE_1)
    LINE -> shop_line (writer SHAPEFILE_1)
    AREA -> shop_polygon (writer SHAPEFILE_1)
    COLLECTION -> shop_geom (writer SHAPEFILE_1)
    NULL -> shop_geom (writer SHAPEFILE_1)
GeometryFilter_25
    BREAK_AGG = Yes
    GEOM_PORT_NAMES = Point Line Area Collection Null
    INSTANTIATE = Yes
    POINT -> tourism_point (writer SHAPEFILE_1)
    LINE -> tourism_line (writer SHAPEFILE_1)
    AREA -> tourism_polygon (writer SHAPEFILE_1)
    COLLECTION -> tourism_geom (writer SHAPEFILE_1)
    NULL -> tourism_geom (writer SHAPEFILE_1)
GeometryFilter_27
    BREAK_AGG = Yes
    GEOM_PORT_NAMES = Point Line Area Collection Null
    INSTANTIATE = Yes
    POINT -> unknown_point (writer SHAPEFILE_1)
    LINE -> unknown_line (writer SHAPEFILE_1)
    AREA -> unknown_polygon (writer SHAPEFILE_1)
    COLLECTION -> unknown_geom (writer SHAPEFILE_1)
    NULL -> unknown_geom (writer SHAPEFILE_1)

Bookmark: Reader Feature Types
aerialway (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, source xml_buffer, aerialway xml_buffer
    -> GeometryFilter
aeroway (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, building xml_buffer, ele xml_buffer, surface xml_buffer, ref xml_buffer, source xml_buffer, aeroway xml_buffer
    -> GeometryFilter_2
waterway (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, source xml_buffer, gnis:feature_id xml_buffer, ele xml_buffer, tunnel xml_buffer, name xml_buffer, waterway xml_buffer
    -> GeometryFilter_28
barrier (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, source xml_buffer, historic xml_buffer, landuse xml_buffer, stile xml_buffer, foot xml_buffer, bicycle xml_buffer, name xml_buffer, barrier xml_buffer
    -> GeometryFilter_4
amenity (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, shelter xml_buffer, ref xml_buffer, ele xml_buffer, gnis:feature_id xml_buffer, gnis:created xml_buffer, gnis:county_id xml_buffer, gnis:state_id xml_buffer, atm xml_buffer, backrest xml_buffer, recycling_type xml_buffer, recycling:glass xml_buffer, support xml_buffer, covered xml_buffer, bicycle_parking xml_buffer, network xml_buffer, brand xml_buffer, religion xml_buffer, wheelchair xml_buffer,
      operator:type xml_buffer, addr:housenumber xml_buffer, shelter_type xml_buffer, vending xml_buffer, sport xml_buffer, note xml_buffer, parking xml_buffer, access xml_buffer, capacity xml_buffer, cuisine xml_buffer, addr:street xml_buffer, social_facility xml_buffer, source xml_buffer, operator xml_buffer, building xml_buffer, amenity xml_buffer
    -> GeometryFilter_3
geological (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, natural xml_buffer, type xml_buffer, geological xml_buffer
    -> GeometryFilter_9
office (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, building xml_buffer, addr:housenumber xml_buffer, office xml_buffer
    -> GeometryFilter_17
boundary (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, admin_level xml_buffer, source xml_buffer, name xml_buffer, protect_class xml_buffer, protection_title xml_buffer, leisure xml_buffer, attribution xml_buffer, note xml_buffer, type xml_buffer, postal_code xml_buffer, boundary xml_buffer
    -> GeometryFilter_5
building (reader OSM_1)
    attributes: created_by xml_buffer, area xml_buffer, tag{}.k xml_buffer, tag{}.v xml_buffer, nd{}.ref xml_buffer, member{}.type xml_buffer, member{}.ref xml_buffer, member{}.role xml_buffer, osm_feature_type xml_buffer, osm_theme xml_buffer, source xml_buffer, military xml_buffer, denomination xml_buffer, ref:ruian:building xml_buffer, building:ruian:type xml_buffer, construction xml_buffer, fixme xml_buffer, tourism xml_buffer, ref:bag xml_buffer, source:date xml_buffer, religion xml_buffer, amenity xml_buffer, start_date xml_buffer, layer xml_buffer, building:use:pl xml_buffer, addr:housenumber xml_buffer, addr:city xml_buffer, addr:postcode xml_buffer, power xml_buffer, substation xml_buffer,
      building:usage:pl xml_buffer, building:levels xml_buffer, name xml_buffer, addr:street xml_buffer, height xml_buffer, building xml_buffer
    -> GeometryFilter_6
craft (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, addr:housenumber xml_buffer, craft xml_buffer
    -> GeometryFilter_7
emergency (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, fire_hydrant:type xml_buffer, fire_hydrant:diameter xml_buffer, fire_hydrant:position xml_buffer, access xml_buffer, operator xml_buffer, highway xml_buffer, name xml_buffer, foot xml_buffer, emergency xml_buffer
    -> GeometryFilter_8
place (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, source xml_buffer, is_in:state_code xml_buffer, is_in:state xml_buffer, wikidata xml_buffer, is_in:country xml_buffer, is_in:country_code xml_buffer, name:en xml_buffer, wikipedia xml_buffer, is_in xml_buffer, landuse xml_buffer, natural xml_buffer, place xml_buffer
    -> GeometryFilter_18
highway (reader OSM_1)
    attributes: created_by xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, maxspeed xml_buffer, service xml_buffer, proposed xml_buffer, crossing xml_buffer, construction xml_buffer, sport xml_buffer, bicycle xml_buffer, foot xml_buffer, level xml_buffer, wheelchair xml_buffer, distance xml_buffer, surface xml_buffer, public_transport xml_buffer, bus xml_buffer, lanes xml_buffer, tiger:cfcc xml_buffer, area xml_buffer, ref xml_buffer, incline xml_buffer,
      direction xml_buffer, tracktype xml_buffer, oneway xml_buffer, source xml_buffer, highway xml_buffer
    -> GeometryFilter_10
historic (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, site_type xml_buffer, ref xml_buffer, building xml_buffer, source xml_buffer, religion xml_buffer, historic xml_buffer
    -> GeometryFilter_11
leisure (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, sport xml_buffer, source xml_buffer, type xml_buffer, access xml_buffer, addr:street xml_buffer, website xml_buffer, boundary xml_buffer, building xml_buffer, name xml_buffer, leisure xml_buffer
    -> GeometryFilter_13
landuse (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, source xml_buffer, massgis:PUB_ACCESS xml_buffer, ownership xml_buffer, owner xml_buffer, leisure xml_buffer, protected xml_buffer, massgis:TOWN_ID xml_buffer, massgis:FEE_OWNER xml_buffer, massgis:ARTICLE97 xml_buffer, natural xml_buffer, water xml_buffer, building xml_buffer, source:date xml_buffer, logging:start_date xml_buffer, type xml_buffer, barrier xml_buffer, name xml_buffer, landuse xml_buffer
    -> GeometryFilter_12
unfiltered (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, unfiltered xml_buffer
    -> GeometryFilter_26
man_made (reader OSM_1)
    attributes: created_by xml_buffer, area xml_buffer, tag{}.k xml_buffer, tag{}.v xml_buffer, nd{}.ref xml_buffer, member{}.type xml_buffer, member{}.ref xml_buffer, member{}.role xml_buffer, osm_feature_type xml_buffer, osm_theme xml_buffer, source xml_buffer, surveillance xml_buffer, surveillance:type xml_buffer, street_cabinet xml_buffer, operator xml_buffer, location xml_buffer, type xml_buffer, layer xml_buffer, tower:type xml_buffer, communication:mobile_phone xml_buffer, building xml_buffer, note xml_buffer, ref xml_buffer, ele xml_buffer, name xml_buffer, man_made xml_buffer
    -> GeometryFilter_14
natural (reader OSM_1)
    attributes: created_by xml_buffer, layer xml_buffer, tag{}.k xml_buffer, tag{}.v xml_buffer, nd{}.ref xml_buffer, member{}.type xml_buffer, member{}.ref xml_buffer, member{}.role xml_buffer, osm_feature_type xml_buffer, osm_theme xml_buffer, source xml_buffer, wetland xml_buffer, golf xml_buffer, area xml_buffer, attribution xml_buffer, type xml_buffer, nhd:com_id xml_buffer, nhd:fdate xml_buffer, ele xml_buffer, mountain_pass xml_buffer, source_ref xml_buffer, LINZ:dataset xml_buffer, LINZ:layer xml_buffer, LINZ:source_version xml_buffer, name xml_buffer, natural xml_buffer
    -> GeometryFilter_16
military (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, building xml_buffer, bunker_type xml_buffer, historic xml_buffer, military xml_buffer
    -> GeometryFilter_15
public_transport (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, bus xml_buffer, highway xml_buffer, network xml_buffer, type xml_buffer, railway xml_buffer, operator xml_buffer, public_transport xml_buffer
    -> GeometryFilter_20
sport (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, leisure xml_buffer, name xml_buffer, golf xml_buffer, landuse xml_buffer, natural xml_buffer, surface xml_buffer, sport xml_buffer
    -> GeometryFilter_24
power (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, source xml_buffer, ref xml_buffer, location xml_buffer, frequency xml_buffer, generator:source xml_buffer, generator:method xml_buffer, generator:output:electricity xml_buffer, cables xml_buffer, name xml_buffer, substation xml_buffer, building xml_buffer, operator xml_buffer, voltage xml_buffer, power xml_buffer
    -> GeometryFilter_19
railway (reader OSM_1)
    attributes: created_by xml_buffer, layer xml_buffer, tag{}.k xml_buffer, tag{}.v xml_buffer, nd{}.ref xml_buffer, member{}.type xml_buffer, member{}.ref xml_buffer, member{}.role xml_buffer, osm_feature_type xml_buffer, osm_theme xml_buffer, gauge xml_buffer, electrified xml_buffer, wheelchair xml_buffer, railway:signal:direction xml_buffer, railway:signal:position xml_buffer, tram xml_buffer, highway xml_buffer, crossing xml_buffer, railway:position xml_buffer, railway:milestone:catenary_mast xml_buffer, area xml_buffer, service xml_buffer, wikipedia xml_buffer, name xml_buffer, public_transport xml_buffer, train xml_buffer, voltage xml_buffer, frequency xml_buffer, ref xml_buffer, railway xml_buffer
    -> GeometryFilter_21
route (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, network xml_buffer, type xml_buffer, name xml_buffer, ref xml_buffer, operator xml_buffer, osmc:symbol xml_buffer, foot xml_buffer, note xml_buffer, highway xml_buffer, voltage xml_buffer, cables xml_buffer, wires xml_buffer, frequency xml_buffer, route xml_buffer
    -> GeometryFilter_22
shop (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, addr:street xml_buffer, source xml_buffer, building xml_buffer, addr:housenumber xml_buffer, shop xml_buffer
    -> GeometryFilter_23
tourism (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, name xml_buffer, information xml_buffer, ele xml_buffer, artwork_type xml_buffer, addr:street xml_buffer, building xml_buffer, tourism xml_buffer
    -> GeometryFilter_25
unknown (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, unknown xml_buffer
    -> GeometryFilter_27

Bookmark: Writer Feature Types
aerialway_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), source varchar(254), aerialway varchar(254)
aerialway_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), source varchar(254), aerialway varchar(254)
aerialway_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), source varchar(254), aerialway varchar(254)
aerialway_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), source varchar(254), aerialway varchar(254)
aeroway_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), building varchar(254), ele varchar(254), surface varchar(254), ref varchar(254), source varchar(254), aeroway varchar(254)
aeroway_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), building varchar(254), ele varchar(254), surface varchar(254), ref varchar(254), source varchar(254), aeroway varchar(254)
aeroway_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), building varchar(254), ele varchar(254), surface varchar(254), ref varchar(254), source varchar(254), aeroway varchar(254)
aeroway_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), building varchar(254), ele varchar(254), surface varchar(254), ref varchar(254), source varchar(254), aeroway varchar(254)
waterway_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), gnis:featu varchar(254), ele varchar(254), tunnel varchar(254), name varchar(254), waterway varchar(254)
waterway_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), gnis:featu varchar(254), ele varchar(254), tunnel varchar(254), name varchar(254), waterway varchar(254)
waterway_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), gnis:featu varchar(254), ele varchar(254), tunnel varchar(254), name varchar(254), waterway varchar(254)
waterway_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), gnis:featu varchar(254), ele varchar(254), tunnel varchar(254), name varchar(254), waterway varchar(254)
barrier_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), historic varchar(254), landuse varchar(254), stile varchar(254), foot varchar(254), bicycle varchar(254), name varchar(254), barrier varchar(254)
barrier_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), historic varchar(254), landuse varchar(254), stile varchar(254), foot varchar(254), bicycle varchar(254), name varchar(254), barrier varchar(254)
barrier_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), historic varchar(254), landuse varchar(254), stile varchar(254), foot varchar(254), bicycle varchar(254), name varchar(254), barrier varchar(254)
barrier_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), historic varchar(254), landuse varchar(254), stile varchar(254), foot varchar(254), bicycle varchar(254), name varchar(254), barrier varchar(254)
amenity_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), shelter varchar(254), ref varchar(254), ele varchar(254), gnis:featu varchar(254), gnis:creat varchar(254), gnis:count varchar(254), gnis:state varchar(254), atm varchar(254), backrest varchar(254), recycling_ varchar(254), recycling: varchar(254),
      support varchar(254), covered varchar(254), bicycle_pa varchar(254), network varchar(254), brand varchar(254), religion varchar(254), wheelchair varchar(254), operator:t varchar(254), addr:house varchar(254), shelter_ty varchar(254), vending varchar(254), sport varchar(254), note varchar(254), parking varchar(254), access varchar(254), capacity varchar(254), cuisine varchar(254), addr:stree varchar(254), social_fac varchar(254), source varchar(254), operator varchar(254), building varchar(254), amenity varchar(254)
amenity_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), shelter varchar(254), ref varchar(254), ele varchar(254), gnis:featu varchar(254), gnis:creat varchar(254), gnis:count varchar(254), gnis:state varchar(254), atm varchar(254), backrest varchar(254), recycling_ varchar(254), recycling: varchar(254),
      support varchar(254), covered varchar(254), bicycle_pa varchar(254), network varchar(254), brand varchar(254), religion varchar(254), wheelchair varchar(254), operator:t varchar(254), addr:house varchar(254), shelter_ty varchar(254), vending varchar(254), sport varchar(254), note varchar(254), parking varchar(254), access varchar(254), capacity varchar(254), cuisine varchar(254), addr:stree varchar(254), social_fac varchar(254), source varchar(254), operator varchar(254), building varchar(254), amenity varchar(254)
amenity_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), shelter varchar(254), ref varchar(254), ele varchar(254), gnis:featu varchar(254), gnis:creat varchar(254), gnis:count varchar(254), gnis:state varchar(254), atm varchar(254), backrest varchar(254), recycling_ varchar(254), recycling: varchar(254),
      support varchar(254), covered varchar(254), bicycle_pa varchar(254), network varchar(254), brand varchar(254), religion varchar(254), wheelchair varchar(254), operator:t varchar(254), addr:house varchar(254), shelter_ty varchar(254), vending varchar(254), sport varchar(254), note varchar(254), parking varchar(254), access varchar(254), capacity varchar(254), cuisine varchar(254), addr:stree varchar(254), social_fac varchar(254), source varchar(254), operator varchar(254), building varchar(254), amenity varchar(254)
amenity_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), shelter varchar(254), ref varchar(254), ele varchar(254), gnis:featu varchar(254), gnis:creat varchar(254), gnis:count varchar(254), gnis:state varchar(254), atm varchar(254), backrest varchar(254), recycling_ varchar(254), recycling: varchar(254),
      support varchar(254), covered varchar(254), bicycle_pa varchar(254), network varchar(254), brand varchar(254), religion varchar(254), wheelchair varchar(254), operator:t varchar(254), addr:house varchar(254), shelter_ty varchar(254), vending varchar(254), sport varchar(254), note varchar(254), parking varchar(254), access varchar(254), capacity varchar(254), cuisine varchar(254), addr:stree varchar(254), social_fac varchar(254), source varchar(254), operator varchar(254), building varchar(254), amenity varchar(254)
geological_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), natural varchar(254), type varchar(254), geological varchar(254)
geological_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), natural varchar(254), type varchar(254), geological varchar(254)
geological_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), natural varchar(254), type varchar(254), geological varchar(254)
geological_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), natural varchar(254), type varchar(254), geological varchar(254)
office_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), building varchar(254), addr:house varchar(254), office varchar(254)
office_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), building varchar(254), addr:house varchar(254), office varchar(254)
office_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), building varchar(254), addr:house varchar(254), office varchar(254)
office_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), building varchar(254), addr:house varchar(254), office varchar(254)
boundary_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), admin_leve varchar(254), source varchar(254), name varchar(254), protect_cl varchar(254), protection varchar(254), leisure varchar(254), attributio varchar(254), note varchar(254), type varchar(254), postal_cod varchar(254), boundary varchar(254)
boundary_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), admin_leve varchar(254), source varchar(254), name varchar(254), protect_cl varchar(254), protection varchar(254), leisure varchar(254), attributio varchar(254), note varchar(254), type varchar(254), postal_cod varchar(254), boundary varchar(254)
boundary_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), admin_leve varchar(254), source varchar(254), name varchar(254), protect_cl varchar(254), protection varchar(254), leisure varchar(254), attributio varchar(254), note varchar(254), type varchar(254), postal_cod varchar(254), boundary varchar(254)
boundary_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), admin_leve varchar(254), source varchar(254), name varchar(254), protect_cl varchar(254), protection varchar(254), leisure varchar(254), attributio varchar(254), note varchar(254), type varchar(254), postal_cod varchar(254), boundary varchar(254)
building_point (writer SHAPEFILE_1)
    attributes: id varchar(254), timestamp varchar(254), user varchar(254), visible varchar(254), created_by varchar(254), area varchar(254), uid varchar(254), version varchar(254), changeset varchar(254), tag___k varchar(254), tag___v varchar(254), nd___ref varchar(254), member___t varchar(254), member___r varchar(254), member__00 varchar(254), osm_featur varchar(254), osm_theme varchar(254), source varchar(254), military varchar(254), denominati varchar(254), ref:ruian: varchar(254), building:r varchar(254), constructi varchar(254), fixme varchar(254), tourism varchar(254), ref:bag varchar(254), source:dat varchar(254), religion varchar(254), amenity varchar(254), start_date varchar(254),
      layer varchar(254), building:u varchar(254), addr:house varchar(254), addr:city varchar(254), addr:postc varchar(254), power varchar(254), substation varchar(254), building00 varchar(254), building:l varchar(254), name varchar(254), addr:stree varchar(254), height varchar(254), building varchar(254)
building_line (writer SHAPEFILE_1)
    attributes: id varchar(254), timestamp varchar(254), user varchar(254), visible varchar(254), created_by varchar(254), area varchar(254), uid varchar(254), version varchar(254), changeset varchar(254), tag___k varchar(254), tag___v varchar(254), nd___ref varchar(254), member___t varchar(254), member___r varchar(254), member__00 varchar(254), osm_featur varchar(254), osm_theme varchar(254), source varchar(254), military varchar(254), denominati varchar(254), ref:ruian: varchar(254), building:r varchar(254), constructi varchar(254), fixme varchar(254), tourism varchar(254), ref:bag varchar(254), source:dat varchar(254), religion varchar(254), amenity varchar(254), start_date varchar(254),
      layer varchar(254), building:u varchar(254), addr:house varchar(254), addr:city varchar(254), addr:postc varchar(254), power varchar(254), substation varchar(254), building00 varchar(254), building:l varchar(254), name varchar(254), addr:stree varchar(254), height varchar(254), building varchar(254)
building_polygon (writer SHAPEFILE_1)
    attributes: id varchar(254), timestamp varchar(254), user varchar(254), visible varchar(254), created_by varchar(254), area varchar(254), uid varchar(254), version varchar(254), changeset varchar(254), tag___k varchar(254), tag___v varchar(254), nd___ref varchar(254), member___t varchar(254), member___r varchar(254), member__00 varchar(254), osm_featur varchar(254), osm_theme varchar(254), source varchar(254), military varchar(254), denominati varchar(254), ref:ruian: varchar(254), building:r varchar(254), constructi varchar(254), fixme varchar(254), tourism varchar(254), ref:bag varchar(254), source:dat varchar(254), religion varchar(254), amenity varchar(254), start_date varchar(254),
      layer varchar(254), building:u varchar(254), addr:house varchar(254), addr:city varchar(254), addr:postc varchar(254), power varchar(254), substation varchar(254), building00 varchar(254), building:l varchar(254), name varchar(254), addr:stree varchar(254), height varchar(254), building varchar(254)
building_geom (writer SHAPEFILE_1)
    attributes: id varchar(254), timestamp varchar(254), user varchar(254), visible varchar(254), created_by varchar(254), area varchar(254), uid varchar(254), version varchar(254), changeset varchar(254), tag___k varchar(254), tag___v varchar(254), nd___ref varchar(254), member___t varchar(254), member___r varchar(254), member__00 varchar(254), osm_featur varchar(254), osm_theme varchar(254), source varchar(254), military varchar(254), denominati varchar(254), ref:ruian: varchar(254), building:r varchar(254), constructi varchar(254), fixme varchar(254), tourism varchar(254), ref:bag varchar(254), source:dat varchar(254), religion varchar(254), amenity varchar(254), start_date varchar(254),
      layer varchar(254), building:u varchar(254), addr:house varchar(254), addr:city varchar(254), addr:postc varchar(254), power varchar(254), substation varchar(254), building00 varchar(254), building:l varchar(254), name varchar(254), addr:stree varchar(254), height varchar(254), building varchar(254)
craft_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), addr:house varchar(254), craft varchar(254)
craft_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), addr:house varchar(254), craft varchar(254)
craft_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), addr:house varchar(254), craft varchar(254)
craft_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), addr:house varchar(254), craft varchar(254)
emergency_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), fire_hydra varchar(254), fire_hyd00 varchar(254), fire_hyd01 varchar(254), access varchar(254), operator varchar(254), highway varchar(254), name varchar(254), foot varchar(254), emergency varchar(254)
emergency_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), fire_hydra varchar(254), fire_hyd00 varchar(254), fire_hyd01 varchar(254), access varchar(254), operator varchar(254), highway varchar(254), name varchar(254), foot varchar(254), emergency varchar(254)
emergency_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), fire_hydra varchar(254), fire_hyd00 varchar(254), fire_hyd01 varchar(254), access varchar(254), operator varchar(254), highway varchar(254), name varchar(254), foot varchar(254), emergency varchar(254)
emergency_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), fire_hydra varchar(254), fire_hyd00 varchar(254), fire_hyd01 varchar(254), access varchar(254), operator varchar(254), highway varchar(254), name varchar(254), foot varchar(254), emergency varchar(254)
place_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), source varchar(254), is_in:stat varchar(254), is_in:st00 varchar(254), wikidata varchar(254), is_in:coun varchar(254), is_in:co00 varchar(254), name:en varchar(254), wikipedia varchar(254), is_in varchar(254), landuse varchar(254), natural varchar(254),
      place varchar(254)
place_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), source varchar(254), is_in:stat varchar(254), is_in:st00 varchar(254), wikidata varchar(254), is_in:coun varchar(254), is_in:co00 varchar(254), name:en varchar(254), wikipedia varchar(254), is_in varchar(254), landuse varchar(254), natural varchar(254),
      place varchar(254)
place_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), source varchar(254), is_in:stat varchar(254), is_in:st00 varchar(254), wikidata varchar(254), is_in:coun varchar(254), is_in:co00 varchar(254), name:en varchar(254), wikipedia varchar(254), is_in varchar(254), landuse varchar(254), natural varchar(254),
      place varchar(254)
place_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), source varchar(254), is_in:stat varchar(254), is_in:st00 varchar(254), wikidata varchar(254), is_in:coun varchar(254), is_in:co00 varchar(254), name:en varchar(254), wikipedia varchar(254), is_in varchar(254), landuse varchar(254), natural varchar(254),
      place varchar(254)
highway_point (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), maxspeed varchar(254), service varchar(254), proposed varchar(254), crossing varchar(254), constructi varchar(254), sport varchar(254), bicycle varchar(254), foot varchar(254), level varchar(254), wheelchair varchar(254), distance varchar(254), surface varchar(254),
      public_tra varchar(254), bus varchar(254), lanes varchar(254), tiger:cfcc varchar(254), area varchar(254), ref varchar(254), incline varchar(254), direction varchar(254), tracktype varchar(254), oneway varchar(254), source varchar(254), highway varchar(254)
highway_line (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), maxspeed varchar(254), service varchar(254), proposed varchar(254), crossing varchar(254), constructi varchar(254), sport varchar(254), bicycle varchar(254), foot varchar(254), level varchar(254), wheelchair varchar(254), distance varchar(254), surface varchar(254),
      public_tra varchar(254), bus varchar(254), lanes varchar(254), tiger:cfcc varchar(254), area varchar(254), ref varchar(254), incline varchar(254), direction varchar(254), tracktype varchar(254), oneway varchar(254), source varchar(254), highway varchar(254)
highway_polygon (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), maxspeed varchar(254), service varchar(254), proposed varchar(254), crossing varchar(254), constructi varchar(254), sport varchar(254), bicycle varchar(254), foot varchar(254), level varchar(254), wheelchair varchar(254), distance varchar(254), surface varchar(254),
      public_tra varchar(254), bus varchar(254), lanes varchar(254), tiger:cfcc varchar(254), area varchar(254), ref varchar(254), incline varchar(254), direction varchar(254), tracktype varchar(254), oneway varchar(254), source varchar(254), highway varchar(254)
highway_geom (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), maxspeed varchar(254), service varchar(254), proposed varchar(254), crossing varchar(254), constructi varchar(254), sport varchar(254), bicycle varchar(254), foot varchar(254), level varchar(254), wheelchair varchar(254), distance varchar(254), surface varchar(254),
      public_tra varchar(254), bus varchar(254), lanes varchar(254), tiger:cfcc varchar(254), area varchar(254), ref varchar(254), incline varchar(254), direction varchar(254), tracktype varchar(254), oneway varchar(254), source varchar(254), highway varchar(254)
historic_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), site_type varchar(254), ref varchar(254), building varchar(254), source varchar(254), religion varchar(254), historic varchar(254)
historic_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), site_type varchar(254), ref varchar(254), building varchar(254), source varchar(254), religion varchar(254), historic varchar(254)
historic_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), site_type varchar(254), ref varchar(254), building varchar(254), source varchar(254), religion varchar(254), historic varchar(254)
historic_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), site_type varchar(254), ref varchar(254), building varchar(254), source varchar(254), religion varchar(254), historic varchar(254)
leisure_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), sport varchar(254), source varchar(254), type varchar(254), access varchar(254), addr:stree varchar(254), website varchar(254), boundary varchar(254), building varchar(254), name varchar(254), leisure varchar(254)
leisure_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), sport varchar(254), source varchar(254), type varchar(254), access varchar(254), addr:stree varchar(254), website varchar(254), boundary varchar(254), building varchar(254), name varchar(254), leisure varchar(254)
leisure_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), sport varchar(254), source varchar(254), type varchar(254), access varchar(254), addr:stree varchar(254), website varchar(254), boundary varchar(254), building varchar(254), name varchar(254), leisure varchar(254)
leisure_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), sport varchar(254), source varchar(254), type varchar(254), access varchar(254), addr:stree varchar(254), website varchar(254), boundary varchar(254), building varchar(254), name varchar(254), leisure varchar(254)
landuse_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), massgis:PU varchar(254), ownership varchar(254), owner varchar(254), leisure varchar(254), protected varchar(254), massgis:TO varchar(254), massgis:FE varchar(254), massgis:AR varchar(254), natural varchar(254), water varchar(254), building varchar(254),
      source:dat varchar(254), logging:st varchar(254), type varchar(254), barrier varchar(254), name varchar(254), landuse varchar(254)
landuse_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), massgis:PU varchar(254), ownership varchar(254), owner varchar(254), leisure varchar(254), protected varchar(254), massgis:TO varchar(254), massgis:FE varchar(254), massgis:AR varchar(254), natural varchar(254), water varchar(254), building varchar(254),
      source:dat varchar(254), logging:st varchar(254), type varchar(254), barrier varchar(254), name varchar(254), landuse varchar(254)
landuse_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), massgis:PU varchar(254), ownership varchar(254), owner varchar(254), leisure varchar(254), protected varchar(254), massgis:TO varchar(254), massgis:FE varchar(254), massgis:AR varchar(254), natural varchar(254), water varchar(254), building varchar(254),
      source:dat varchar(254), logging:st varchar(254), type varchar(254), barrier varchar(254), name varchar(254), landuse varchar(254)
landuse_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), massgis:PU varchar(254), ownership varchar(254), owner varchar(254), leisure varchar(254), protected varchar(254), massgis:TO varchar(254), massgis:FE varchar(254), massgis:AR varchar(254), natural varchar(254), water varchar(254), building varchar(254),
      source:dat varchar(254), logging:st varchar(254), type varchar(254), barrier varchar(254), name varchar(254), landuse varchar(254)
unfiltered_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), unfiltered varchar(254)
unfiltered_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), unfiltered varchar(254)
unfiltered_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), unfiltered varchar(254)
unfiltered_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), unfiltered varchar(254)
man_made_point (writer SHAPEFILE_1)
    attributes: id varchar(254), timestamp varchar(254), user varchar(254), visible varchar(254), created_by varchar(254), area varchar(254), uid varchar(254), version varchar(254), changeset varchar(254), tag___k varchar(254), tag___v varchar(254), nd___ref varchar(254), member___t varchar(254), member___r varchar(254), member__00 varchar(254), osm_featur varchar(254), osm_theme varchar(254), source varchar(254), surveillan varchar(254), surveill00 varchar(254), street_cab varchar(254), operator varchar(254), location varchar(254), type varchar(254), layer varchar(254), tower:type varchar(254), communicat varchar(254), building varchar(254), note varchar(254), ref varchar(254),
      ele varchar(254), name varchar(254), man_made varchar(254)
man_made_line (writer SHAPEFILE_1)
    attributes: id varchar(254), timestamp varchar(254), user varchar(254), visible varchar(254), created_by varchar(254), area varchar(254), uid varchar(254), version varchar(254), changeset varchar(254), tag___k varchar(254), tag___v varchar(254), nd___ref varchar(254), member___t varchar(254), member___r varchar(254), member__00 varchar(254), osm_featur varchar(254), osm_theme varchar(254), source varchar(254), surveillan varchar(254), surveill00 varchar(254), street_cab varchar(254), operator varchar(254), location varchar(254), type varchar(254), layer varchar(254), tower:type varchar(254), communicat varchar(254), building varchar(254), note varchar(254), ref varchar(254),
      ele varchar(254), name varchar(254), man_made varchar(254)
man_made_polygon (writer SHAPEFILE_1)
    attributes: id varchar(254), timestamp varchar(254), user varchar(254), visible varchar(254), created_by varchar(254), area varchar(254), uid varchar(254), version varchar(254), changeset varchar(254), tag___k varchar(254), tag___v varchar(254), nd___ref varchar(254), member___t varchar(254), member___r varchar(254), member__00 varchar(254), osm_featur varchar(254), osm_theme varchar(254), source varchar(254), surveillan varchar(254), surveill00 varchar(254), street_cab varchar(254), operator varchar(254), location varchar(254), type varchar(254), layer varchar(254), tower:type varchar(254), communicat varchar(254), building varchar(254), note varchar(254), ref varchar(254),
      ele varchar(254), name varchar(254), man_made varchar(254)
man_made_geom (writer SHAPEFILE_1)
    attributes: id varchar(254), timestamp varchar(254), user varchar(254), visible varchar(254), created_by varchar(254), area varchar(254), uid varchar(254), version varchar(254), changeset varchar(254), tag___k varchar(254), tag___v varchar(254), nd___ref varchar(254), member___t varchar(254), member___r varchar(254), member__00 varchar(254), osm_featur varchar(254), osm_theme varchar(254), source varchar(254), surveillan varchar(254), surveill00 varchar(254), street_cab varchar(254), operator varchar(254), location varchar(254), type varchar(254), layer varchar(254), tower:type varchar(254), communicat varchar(254), building varchar(254), note varchar(254), ref varchar(254),
      ele varchar(254), name varchar(254), man_made varchar(254)
natural_point (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), wetland varchar(254), golf varchar(254), area varchar(254), attributio varchar(254), type varchar(254), nhd:com_id varchar(254), nhd:fdate varchar(254), ele varchar(254), mountain_p varchar(254), source_ref varchar(254), LINZ:datas varchar(254), LINZ:layer varchar(254),
      LINZ:sourc varchar(254), name varchar(254), natural varchar(254)
natural_line (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), wetland varchar(254), golf varchar(254), area varchar(254), attributio varchar(254), type varchar(254), nhd:com_id varchar(254), nhd:fdate varchar(254), ele varchar(254), mountain_p varchar(254), source_ref varchar(254), LINZ:datas varchar(254), LINZ:layer varchar(254),
      LINZ:sourc varchar(254), name varchar(254), natural varchar(254)
natural_polygon (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), wetland varchar(254), golf varchar(254), area varchar(254), attributio varchar(254), type varchar(254), nhd:com_id varchar(254), nhd:fdate varchar(254), ele varchar(254), mountain_p varchar(254), source_ref varchar(254), LINZ:datas varchar(254), LINZ:layer varchar(254),
      LINZ:sourc varchar(254), name varchar(254), natural varchar(254)
natural_geom (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), wetland varchar(254), golf varchar(254), area varchar(254), attributio varchar(254), type varchar(254), nhd:com_id varchar(254), nhd:fdate varchar(254), ele varchar(254), mountain_p varchar(254), source_ref varchar(254), LINZ:datas varchar(254), LINZ:layer varchar(254),
      LINZ:sourc varchar(254), name varchar(254), natural varchar(254)
military_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), building varchar(254), bunker_typ varchar(254), historic varchar(254), military varchar(254)
military_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), building varchar(254), bunker_typ varchar(254), historic varchar(254), military varchar(254)
military_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), building varchar(254), bunker_typ varchar(254), historic varchar(254), military varchar(254)
military_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), building varchar(254), bunker_typ varchar(254), historic varchar(254), military varchar(254)
public_transport_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), bus varchar(254), highway varchar(254), network varchar(254), type varchar(254), railway varchar(254), operator varchar(254), public_tra varchar(254)
public_transport_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), bus varchar(254), highway varchar(254), network varchar(254), type varchar(254), railway varchar(254), operator varchar(254), public_tra varchar(254)
public_transport_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), bus varchar(254), highway varchar(254), network varchar(254), type varchar(254), railway varchar(254), operator varchar(254), public_tra varchar(254)
public_transport_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), bus varchar(254), highway varchar(254), network varchar(254), type varchar(254), railway varchar(254), operator varchar(254), public_tra varchar(254)
sport_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), leisure varchar(254), name varchar(254), golf varchar(254), landuse varchar(254), natural varchar(254), surface varchar(254), sport varchar(254)
sport_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), leisure varchar(254), name varchar(254), golf varchar(254), landuse varchar(254), natural varchar(254), surface varchar(254), sport varchar(254)
sport_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), leisure varchar(254), name varchar(254), golf varchar(254), landuse varchar(254), natural varchar(254), surface varchar(254), sport varchar(254)
sport_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), leisure varchar(254), name varchar(254), golf varchar(254), landuse varchar(254), natural varchar(254), surface varchar(254), sport varchar(254)
power_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), ref varchar(254), location varchar(254), frequency varchar(254), generator: varchar(254), generato00 varchar(254), generato01 varchar(254), cables varchar(254), name varchar(254), substation varchar(254), building varchar(254), operator varchar(254),
      voltage varchar(254), power varchar(254)
power_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), ref varchar(254), location varchar(254), frequency varchar(254), generator: varchar(254), generato00 varchar(254), generato01 varchar(254), cables varchar(254), name varchar(254), substation varchar(254), building varchar(254), operator varchar(254),
      voltage varchar(254), power varchar(254)
power_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), ref varchar(254), location varchar(254), frequency varchar(254), generator: varchar(254), generato00 varchar(254), generato01 varchar(254), cables varchar(254), name varchar(254), substation varchar(254), building varchar(254), operator varchar(254),
      voltage varchar(254), power varchar(254)
power_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), source varchar(254), ref varchar(254), location varchar(254), frequency varchar(254), generator: varchar(254), generato00 varchar(254), generato01 varchar(254), cables varchar(254), name varchar(254), substation varchar(254), building varchar(254), operator varchar(254),
      voltage varchar(254), power varchar(254)
railway_point (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), gauge varchar(254), electrifie varchar(254), wheelchair varchar(254), railway:si varchar(254), railway:00 varchar(254), tram varchar(254), highway varchar(254), crossing varchar(254), railway:po varchar(254), railway:mi varchar(254), area varchar(254), service varchar(254), wikipedia varchar(254),
      name varchar(254), public_tra varchar(254), train varchar(254), voltage varchar(254), frequency varchar(254), ref varchar(254), railway varchar(254)
railway_line (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), gauge varchar(254), electrifie varchar(254), wheelchair varchar(254), railway:si varchar(254), railway:00 varchar(254), tram varchar(254), highway varchar(254), crossing varchar(254), railway:po varchar(254), railway:mi varchar(254), area varchar(254), service varchar(254), wikipedia varchar(254),
      name varchar(254), public_tra varchar(254), train varchar(254), voltage varchar(254), frequency varchar(254), ref varchar(254), railway varchar(254)
railway_polygon (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), gauge varchar(254), electrifie varchar(254), wheelchair varchar(254), railway:si varchar(254), railway:00 varchar(254), tram varchar(254), highway varchar(254), crossing varchar(254), railway:po varchar(254), railway:mi varchar(254), area varchar(254), service varchar(254), wikipedia varchar(254),
      name varchar(254), public_tra varchar(254), train varchar(254), voltage varchar(254), frequency varchar(254), ref varchar(254), railway varchar(254)
railway_geom (writer SHAPEFILE_1)
    attributes: id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), gauge varchar(254), electrifie varchar(254), wheelchair varchar(254), railway:si varchar(254), railway:00 varchar(254), tram varchar(254), highway varchar(254), crossing varchar(254), railway:po varchar(254), railway:mi varchar(254), area varchar(254), service varchar(254), wikipedia varchar(254),
      name varchar(254), public_tra varchar(254), train varchar(254), voltage varchar(254), frequency varchar(254), ref varchar(254), railway varchar(254)
route_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), network varchar(254), type varchar(254), name varchar(254), ref varchar(254), operator varchar(254), osmc:symbo varchar(254), foot varchar(254), note varchar(254), highway varchar(254), voltage varchar(254), cables varchar(254), wires varchar(254),
      frequency varchar(254), route varchar(254)
route_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), network varchar(254), type varchar(254), name varchar(254), ref varchar(254), operator varchar(254), osmc:symbo varchar(254), foot varchar(254), note varchar(254), highway varchar(254), voltage varchar(254), cables varchar(254), wires varchar(254),
      frequency varchar(254), route varchar(254)
route_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), network varchar(254), type varchar(254), name varchar(254), ref varchar(254), operator varchar(254), osmc:symbo varchar(254), foot varchar(254), note varchar(254), highway varchar(254), voltage varchar(254), cables varchar(254), wires varchar(254),
      frequency varchar(254), route varchar(254)
route_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), network varchar(254), type varchar(254), name varchar(254), ref varchar(254), operator varchar(254), osmc:symbo varchar(254), foot varchar(254), note varchar(254), highway varchar(254), voltage varchar(254), cables varchar(254), wires varchar(254),
      frequency varchar(254), route varchar(254)
shop_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), source varchar(254), building varchar(254), addr:house varchar(254), shop varchar(254)
shop_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), source varchar(254), building varchar(254), addr:house varchar(254), shop varchar(254)
shop_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), source varchar(254), building varchar(254), addr:house varchar(254), shop varchar(254)
shop_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), addr:stree varchar(254), source varchar(254), building varchar(254), addr:house varchar(254), shop varchar(254)
tourism_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), informatio varchar(254), ele varchar(254), artwork_ty varchar(254), addr:stree varchar(254), building varchar(254), tourism varchar(254)
tourism_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), informatio varchar(254), ele varchar(254), artwork_ty varchar(254), addr:stree varchar(254), building varchar(254), tourism varchar(254)
tourism_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), informatio varchar(254), ele varchar(254), artwork_ty varchar(254), addr:stree varchar(254), building varchar(254), tourism varchar(254)
tourism_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), informatio varchar(254), ele varchar(254), artwork_ty varchar(254), addr:stree varchar(254), building varchar(254), tourism varchar(254)
unknown_point (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), unknown varchar(254)
unknown_line (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), unknown varchar(254)
unknown_polygon (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), unknown varchar(254)
unknown_geom (writer SHAPEFILE_1)
    attributes: id varchar(254), timestamp varchar(254), user varchar(254), visible varchar(254), created_by varchar(254), area varchar(254), layer varchar(254), uid varchar(254), version varchar(254), changeset varchar(254), tag___k varchar(254), tag___v varchar(254), nd___ref varchar(254), member___t varchar(254), member___r varchar(254), member__00 varchar(254), osm_featur varchar(254), osm_theme varchar(254), unknown varchar(254)
