FME workspace GAP_Issues-Ver-02_DGN&TIFF_fmw.fmw

Parameters:
- FEATURE_TYPES =
- FEATURE_TYPES_2 =
- SourceDataset_DGNV8 =
- SourceDataset_GEOTIFF =

Readers:
- DGNV8_1: DGNV8 from $(SourceDataset_DGNV8)
- GEOTIFF_1: GEOTIFF from $(SourceDataset_GEOTIFF)

GEOTIFF (reader GEOTIFF_1)
    -> BoundingBoxReplacer
BoundingBoxReplacer
    BOXTYPE = 2D Oriented Bounding Box
    BOX -> AreaCalculator
AreaCalculator
    AREA_ATTR = _area
    AREA_TYPE = Plane Area
    MULT = 1
    -> Tester_3
Tester_3
    BOOL_OP = OR
    COMPOSITE_TEST = 1
    TEST_CLAUSE = TEST @Value(_area) = 1000000
    TEST_MODE = TEST
    PASSED -> CoordinateExtractor
    PASSED -> Dissolver
    FAILED -> AttributeCreator_2
CoordinateExtractor
    LIST_NAME = _indices
    MODE = All Coordinates
    -> AttributeCreator
AttributeCreator
    ATTR_TABLE = SET_TO Tile_Name = @Value(fme_basename)
    -> ListConcatenator_3
ListConcatenator_3
    DROP_EMPTY_PARTS = No
    LIST_ATTR = _indices{}.x
    SEP = ,
    VAL_ATTR = GTX_concatenated
    -> ListConcatenator_4
ListConcatenator_4
    DROP_EMPTY_PARTS = No
    LIST_ATTR = _indices{}.y
    SEP = ,
    VAL_ATTR = GTY_concatenated
    -> FeatureJoiner [LEFT]
AttributeCreator_2
    ATTR_TABLE:
      SET_TO igds_level_name = Err_Less_Tile_Size
      SET_TO igds_level = Err_Less_Tile_Size
    -> Errors
Dissolver
    ACCUM_INPUT_ATTRS = Use Attributes From One Feature
    CLEANING_TOLERANCE = Automatic
    CONNECT_Z_MODE = First Wins
    DEAGGREGATE_INPUT = Yes
    AREA -> Bufferer
    AREA -> Clipper_2 [CLIPPEE]
Bufferer
    ANGLE = 22.5
    CAP_STYLE = Arc
    CORNER_STYLE = Arc
    MODE = AREA
    OFFSET = -0.5
    OFFSET_UNITS = NONE
    PRECISION = APPROX
    BUFFERED -> Clipper_2 [CLIPPER]
Clipper_2
    BOUNDARY_CASES = Treat as Inside
    CLEANING_TOLERANCE = None
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    OUTSIDE -> AttributeCreator_6
AttributeCreator_6
    ATTR_TABLE = SET_TO WE = 1
    -> Clipper_3 [CLIPPER]
    -> NodeValence [Line]
4I_Tiles_Delivered (reader DGNV8_1)
    -> AttributeFilter
AttributeFilter
    ATTR_NAME = igds_level_name
    ATTR_VALUES = <Empty>,<Missing>,<Null>,<Unfiltered>,Water,Island,4I_Tiles_Delivered
    Water -> Junction
    Island -> Junction
    4I_Tiles_Delivered -> GeometryFilter
GeometryFilter
    BREAK_AGG = No
    GEOM_PORT_NAMES = Area Text
    AREA -> SpatialFilter [Candidate]
    TEXT -> SpatialFilter [Filter]
SpatialFilter
    AGGREGATE_HANDLING = Yes
    ATTR_ACCUM_MODE = Prefix Filter
    ATTR_PREFIX = _T_
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager
    FAILED -> AttributeCreator_5
AttributeManager
    ATTR_TABLE:
      REMOVE _T_fme_feature_type
      RENAME_SET_VALUE _T_fme_text_string > Tile_Name
      REMOVE _T_fme_rotation
      REMOVE _T_fme_text_size
      REMOVE fme_feature_type
      REMOVE fme_basename
      REMOVE fme_text_string
      REMOVE igds_element_id
      REMOVE igds_level
      REMOVE igds_level_name
      REMOVE igds_text_string{}
      REMOVE _predicate
    -> CoordinateExtractor_2
CoordinateExtractor_2
    LIST_NAME = _indices
    MODE = All Coordinates
    -> ListConcatenator
ListConcatenator
    DROP_EMPTY_PARTS = No
    LIST_ATTR = _indices{}.x
    SEP = ,
    VAL_ATTR = X_concatenated
    -> ListConcatenator_2
ListConcatenator_2
    DROP_EMPTY_PARTS = No
    LIST_ATTR = _indices{}.y
    SEP = ,
    VAL_ATTR = Y_concatenated
    -> FeatureJoiner [RIGHT]
FeatureJoiner
    ATTR_CONFLICT_RES = Use Left
    GEOMETRY_HANDLING = Use Left
    GROUP_BY = Tile_Name
    JOIN_KEYS = GTX_concatenated X_concatenated AUTO
    JOIN_MODE = Full
    JOINED -> Tester
Tester
    BOOL_OP = AND
    COMPOSITE_TEST = 1 AND 2
    TEST_CLAUSE:
      TEST @Value(GTX_concatenated) = @Value(X_concatenated)
      TEST @Value(GTY_concatenated) = @Value(Y_concatenated)
    TEST_MODE = TEST
    FAILED -> AttributeCreator_4
AttributeCreator_4
    ATTR_TABLE:
      SET_TO igds_level_name = Err_GAP_Issues
      SET_TO igds_level = Err_GAP_Issues
    -> Errors
AttributeCreator_5
    ATTR_TABLE:
      SET_TO igds_level_name = Err_Input_AOI_DGN_NO_TXT
      SET_TO igds_level = Err_Input_AOI_DGN_NO_TXT
Junction
    -> GeometryCoercer
GeometryCoercer
    GQUERY:
      for $geom in //geometry
      where $geom/count(parent::geometry) = 0
      return number($geom/@fme_id)
    KIND = fme_line
    COERCED -> Clipper_3 [CLIPPEE]
Clipper_3
    BOUNDARY_CASES = Treat as Inside and Outside
    CLEANING_TOLERANCE = Automatic
    CLIPPED_ATTR = _clipped
    CLIP_TYPE = Multiple Clippers
    LINES_AS_SEGMENTS = Yes
    MEASURE_TYPE = Continuous
    MISSING_VAL_MODE = Compute
    PRESERVE_CLIPPEE_EXTENTS = No
    VAL_SOURCE = Clippee Only
    INSIDE -> NodeValence [Line]
NodeValence
    Node -> Tester_5
Tester_5
    BOOL_OP = OR
    COMPOSITE_TEST = 1 OR 2
    TEST_CLAUSE:
      TEST @Value(valence) = 2
      TEST @Value(valence) = 3
    TEST_MODE = TEST
    FAILED -> AttributeCreator_3
AttributeCreator_3
    ATTR_TABLE:
      SET_TO igds_level_name = Check_Vector_Not_Compiled_Till_AOI
      SET_TO igds_level = Check_Vector_Not_Compiled_Till_AOI
    -> Errors
Errors: Inspector

FME custom transformer NodeValence
Notes
    This transformer builds arc-node topology in attributes to mimic
    ARC/INFO
    Coverage network topology and adds 
    valence
    . See 
        topology_basics
    for some good diagrams and further discussion. After editing or filtering this process needs to be rerun, just like an
    ARC/INFO Build
    command to rebuild the correct relationships with new feature counts. The original system keys all ended in "#". The topology stack was stored as a series of layers inside a single dataset called a
    coverage
    .
    The lines have topology attributes exposed in the
    AAT
    table and nodes have attributes in the 
    NAT
    table, hence the suffix names 
    _aat
    and 
    _nat
    . The two featuretypes (lines and points) are intended to be considered as a single set. Not included in the
    AAT
    table is polygon topology which would contain the LPOLY# and RPOLY# identifiers.
    This process includes the equivalent of
    CLEAN
    which breaks all arcs at junctions, explodes all multiparts, removes all coincident lines and vertices.
    The addition of a 
    valence
    to the 
    NAT
    table is useful for analysis to classify
    dangles
    (1),
    pseudonodes
    (2),
    tees
    (3),
    intersections
    (4) or
    multiple junctions 
    (>4)
    .
    The arcs (lines) contain a foreign key to the 
    node_id
    in the 
    fnode
    and 
    tnode
    attributes to allow arcs to be tested for 
    direction 
    relative to the nodes.
    * Indexing the keys will be essential for reasonable performance when selecting or joining these two tables. Indexing in 
    ARC/INFO
    is implied because the original keys with a "#" in the name are the record number similiar to OBJECTID.
    * Tolerance defaults to 0.1 metre
    * The 
    arc_id
    is just one of the arcs joining the node as in the original model.
    * If arcs are not already split they will be split and therefore will duplicate existing attributes.
    * The fme_feature_ type is used to name the outputs the same as the source featuretype with a suffix _aat and _nat
Input is a branched polyline network <ft>
    Output is a cleaned line featuretype <ft>_aat and point representing nodes <ft>_nat
lines (PK arc_id) have fnode_id and tnode_id
nodes have node_id and valence and arc_id as first connecting arc
    Valence is a count of the number of arcs connecting at a node.

Note: Notes / This transformer builds arc-node topology in attributes to mimic ARC/INFO Coverage network topology and adds valence. See topology_basics for some good diagrams and further discussion. After editing or filtering this process needs to be rerun, just like an ARC/INFO Build command to rebuild the correct relationships with new feature counts. The original system keys all ended in "#". The topology stack was stored as a series of layers inside a single dataset called a coverage. / The lines have topology attributes exposed in the AAT table and nodes have attributes in the NAT table, hence the suffix names _aat and _nat. The two featuretypes (lines and points) are intended to be considered as a single set. Not included in the AAT table is polygon topology which would contain the LPOLY# and RPOLY# identifiers. / This process includes the equivalent of CLEAN which breaks all arcs at junctions, explodes all multiparts, removes all coincident lines and vertices. / The addition of a valence to the NAT table is useful for analysis to classify dangles (1), pseudonodes (2), tees (3), intersections (4) or multiple junctions (>4). / The arcs (lines) contain a foreign key to the node_id in the fnode and tnode attributes to allow arcs to be tested for direction relative to the nodes. / * Indexing the keys will be essential for reasonable performance when selecting or joining these two tables. Indexing in ARC/INFO is implied because the original keys with a "#" in the name are the record number similiar to OBJECTID. / * Tolerance defaults to 0.1 metre / * The arc_id is just one of the arcs joining the node as in the original model. / * If arcs are not already split they will be split and therefore will duplicate existing attributes. / * The fme_feature_ type is used to name the outputs the same as the source featuretype with a suffix _aat and _nat
Line (input)
    -> AttributeExposer

Bookmark: New Bookmark
Note: Splits arcs if not already split at intersections before assigning unique IDs which is transferred to the node. / Creates a point at every intersection and ends of every arc. Does not duplicate points at common junctions thank goodness / Adds a list of arcs connected to each node for the valence calculator
AttributeExposer
    ATTR_LIST = fme_feature_type
    -> First_Intersector
First_Intersector: Intersector
    DUPLICATE_Z_NODES = No
    LIST_NAME = all_reaches
    OV_ATTR = _overlaps
    PERFORM_SELF_INTERSECTION = No
    SEG_ATTR = _segments
    SEPARATE_COLLINEAR_SEGMENTS = No
    INTERSECTED -> arc_id_counter
arc_id_counter: Counter
    CNT_ATTR = arc_id
    DOMAIN = counter
    SCOPE = Local
    START = 1
    -> Intersector
Intersector
    DUPLICATE_Z_NODES = No
    LIST_NAME = all_reaches
    OV_ATTR = _overlaps
    PERFORM_SELF_INTERSECTION = No
    SEG_ATTR = _segments
    SEPARATE_COLLINEAR_SEGMENTS = No
    INTERSECTED -> Snipper_Begin
    INTERSECTED -> FeatureMerger_2 [REQUESTOR]
    NODE -> Node_id_counter

Bookmark: Distinguish between FNODE and TNODE (NeighborhoodPair does not)
Note: Snipper gets the first and last points. / Geohash is a spatial key to test for spatial coincidence with the nodes
Snipper_Begin
    ENDVERTEXATTR = 0
    SNIPMODE = Vertex
    STARTVERTEXATTR = 0
    -> Geohash_Begin
    REMNANTS -> Snipper_End
Geohash_Begin: GeometryExtractor
    ATTR = from_geohash
    GEOHASH_PRECISION_DISPLAY = ~9.3 mm (12 characters)
    KIND_LONG = Geohash
    OGC_WKT_PRECISION_DISPLAY = Shortened 64-bit
    -> FeatureMerger [REQUESTOR]
Snipper_End
    ENDVERTEXATTR = -1
    SNIPMODE = Vertex
    STARTVERTEXATTR = -1
    -> Geohash_End
Geohash_End: GeometryExtractor
    ATTR = to_geohash
    GEOHASH_PRECISION_DISPLAY = ~9.3 mm (12 characters)
    KIND_LONG = Geohash
    OGC_WKT_PRECISION_DISPLAY = Shortened 64-bit
    -> FeatureMerger_3 [REQUESTOR]
Geohash_node: GeometryExtractor
    ATTR = node_geohash
    GEOHASH_PRECISION_DISPLAY = ~9.3 mm (12 characters)
    KIND_LONG = Geohash
    OGC_WKT_PRECISION_DISPLAY = Shortened 64-bit
    -> FeatureMerger [SUPPLIER]
    -> FeatureMerger_3 [SUPPLIER]

Bookmark: Add node_id and valence
Node_id_counter: Counter
    CNT_ATTR = node_id
    DOMAIN = counter2
    SCOPE = Local
    START = 1
    -> ListElementCounter
Note: Valence
ListElementCounter
    CNT_ATTR = valence
    LIST_NAME = all_reaches{}
    -> AttributeKeeper
    -> Geohash_node
Note: Calculates the valence from the hidden list of arc-ids. / Output the nodes with unique ids. / arc_id is simply one of the connected arcs.
AttributeKeeper
    CREATE_BULK_MODE_FEATURES = No
    KEEP_ATTRS = arc_id,network_id,node_id,valence,fme_feature_type
    -> Node (output)

Bookmark: From Node
FeatureMerger
    ATTR_ACCUM_MODE = Merge Supplier
    ATTR_CONFLICT_RES = Use Requestor
    IGNORE_NULLS = No
    JOIN_KEYS = @Value(from_geohash) @Value(node_geohash) AUTO
    MERGE_TYPE = Attributes Only
    PROCESS_DUPS = No
    SUPPLIERS_FIRST = No
    MERGED -> AttributeCreator
Note: Join back the node_id as the from-node based on a Geohash match
AttributeCreator
    ATTR_LIST = fnode_id,@Value(node_id)
    -> AttributeKeeper_2
AttributeKeeper_2
    CREATE_BULK_MODE_FEATURES = No
    KEEP_ATTRS = arc_id,fnode_id
    -> FeatureMerger_2 [SUPPLIER]
FeatureMerger_2
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> FeatureMerger_4 [REQUESTOR]

Bookmark: To Node
FeatureMerger_3
    ATTR_ACCUM_MODE = Merge Supplier
    ATTR_CONFLICT_RES = Use Requestor
    IGNORE_NULLS = No
    JOIN_KEYS = @Value(to_geohash) @Value(node_geohash) AUTO
    MERGE_TYPE = Attributes Only
    PROCESS_DUPS = No
    SUPPLIERS_FIRST = No
    MERGED -> AttributeCreator_2
Note: Join back the node_id as the to-node based on a Geohash match
AttributeCreator_2
    ATTR_LIST = tnode_id,@Value(node_id)
    -> AttributeKeeper_3
AttributeKeeper_3
    CREATE_BULK_MODE_FEATURES = No
    KEEP_ATTRS = arc_id,tnode_id
    -> FeatureMerger_4 [SUPPLIER]
FeatureMerger_4
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> AttributeRemover

Bookmark: Tidy temp attributes
AttributeRemover
    LIST_ATTRS = all_reaches{} all_reaches{}.arc_id all_reaches{}.direction all_reaches{}.fme_basename all_reaches{}.ID all_reaches{}.name all_reaches{}.network_id all_reaches{}.OBJECTID all_reaches{}.SHAPE_Length
    REMOVE_ATTRS = _overlaps,_segments
    -> Arc (output)
Arc (output)

Bookmark: Write Nodes
Node (output)
