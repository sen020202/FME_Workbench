FME workspace Validation_Contour.fmw

Parameters:
- DestDataset_ESRISHAPE = $(FME_MF_DIR)Out   # Destination Esri Shapefile Folder
- SourceDataset_ESRISHAPE = $(FME_MF_DIR)Cont_10km_1300_-1000.shp   # Source Esri Shapefile(s)

Readers:
- ESRISHAPE_1: ESRISHAPE from $(SourceDataset_ESRISHAPE) in EPSG:32636

Writers:
- ESRISHAPE_2: ESRISHAPE to $(DestDataset_ESRISHAPE)

Cont_10km_1400_0000 (reader ESRISHAPE_1)
    attributes: Id long, Layer char(16)
    -> Counter
Counter
    CNT_ATTR = Id
    DOMAIN = @Value(fme_basename)
    SCOPE = Local
    START = 1
    -> AttributeExposer
AttributeExposer
    ATTR_LIST = Id,Layer
    -> AttributeManager
AttributeManager
    ATTR_TABLE = SET_TO Id = @Value(Id)
    -> ElevationExtractor
ElevationExtractor
    ELE_ATTR = Z
    -> Tester
Tester
    BOOL_OP = OR
    TEST_CLAUSE:
      CASE_INSENSITIVE_TEST @Value(Z) ENDS_WITH 25
      CASE_INSENSITIVE_TEST @Value(Z) ENDS_WITH 50
      CASE_INSENSITIVE_TEST @Value(Z) ENDS_WITH 75
      CASE_INSENSITIVE_TEST @Value(Z) ENDS_WITH 00
    PASSED -> AttributeCreator
    FAILED -> AttributeCreator_2
AttributeCreator
    ATTR_TABLE = SET_TO Layer = Index_Contour
    -> Shapefile1 (writer ESRISHAPE_2)
AttributeCreator_2
    ATTR_TABLE = SET_TO Layer = Intermediate_Con
    -> Shapefile1 (writer ESRISHAPE_2)
Shapefile1 (writer ESRISHAPE_2)
    attributes: Id long, Layer char(16), Z float
