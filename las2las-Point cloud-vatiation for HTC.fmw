FME workspace las2las-Point cloud-vatiation for HTC.fmw

Parameters:
- DestDataset_LAS =
- SourceDataset_LAS =

Readers:
- LAS_1: LAS from $(SourceDataset_LAS)

Writers:
- LAS_2: LAS to $(DestDataset_LAS)

LAS (reader LAS_1)
    -> PointCloudComponentKeeper
PointCloudComponentKeeper
    COMPONENTS_TO_KEEP = x,y,z,color_red,color_green,color_blue
    -> PointCloudCoercer
PointCloudCoercer
    ACCUM_ATTRS_NAME = Yes
    CONVERT_TO_DISPLAY = Individual Points
    PART_NUMBER_ATTR_NAME = _part_number
    POINT_COMPONENTS = color_red color_green color_blue
    POINT_COMPONENTS_PRESERVE_DISPLAY = Attributes
    COERCED -> Tester
Tester
    BOOL_OP = OR
    COMPOSITE_TEST = 1
    TEST_CLAUSE = TEST @Value(fme_color) <= 0.69
    TEST_MODE = TEST
    FAILED -> PointCloudCombiner
    FAILED -> Aggregator
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> GeometryCoercer
GeometryCoercer
    GQUERY:
      for $geom in //geometry
      where $geom/count(parent::geometry) = 0
      return number($geom/@fme_id)
    KIND = fme_point_cloud
    COERCED -> File1 (writer LAS_2)
File1 (writer LAS_2)
PointCloudCombiner
    ACCUM_ATTRS_NAME = Yes
    EXTRACT_RASTER_NODATA_NAME = No
    SPACING = 1.0
