FME workspace cityGML2CityGML_New.fmw

Parameters:
- SourceDataset_CITYGML = ""E:\33_Mölndal\Nytt_20211007_3\00_Individual\81.gml" "E:\33_Mölndal\Nytt_20211007_3\00_Individual\992.gml" "E:\33_Mölndal\Nytt_20211007_3\00_Individual\1046.gml" "E:\33_Mölndal\Nytt_20211007_3\00_Individual\1306.gml" "E:\33_Mölndal\Nytt_20211007_3\00_Individual\1307.gml" "E:\33_Mölndal\Nytt_20211007_3\00_Individual\1470.gml" "E:\33_Mölndal\Nytt_20211007_3\00_Individual\1724.gml" "E:\33_Mölndal\Nytt_20211007_3\00_Individual\2341.gml" "E:\33_Mölndal\Nytt_20211007_3\00_Individual\2384.gml" "E:\33_Mölndal\Nytt_20211007_3\00_Individual\2434.gml" "E:\33_Mölndal\Nytt_20211007_3\00_Individual\2513.gml" "E:\33_Mölndal\Nytt_20211007_3\00_Individual\2585.gml" "E:\33_Mölndal\Nytt_20211007_3\00_Individual\2656.gml" "E:\33_Mölndal\Nytt_20211007_3\00_Individual\2658.gml" "E:\33_Mölndal\Nytt_20211007_3\00_Individual\3053.gml" "E:\33_Mölndal\Nytt_20211007_3\00_Individual\3106.gml" "E:\33_Mölndal\Nytt_20211007_3\00_Individual\3142.gml" "E:\33_Mölndal\Nytt_20211007_3\00_Individual\3335.gml" "E:\33_Mölndal\Nytt_20211007_3\00_Individual\3429.gml" "E:\33_Mölndal\Nytt_20211007_3\00_Individual\3548.gml" "E:\33_Mölndal\Nytt_20211007_3\00_Individual\3695.gml" "E:\33_Mölndal\Nytt_20211007_3\00_Individual\3784.gml" "E:\33_Mölndal\Nytt_20211007_3\00_Individual\4035.gml" "E:\33_Mölndal\Nytt_20211007_3\00_Individual\4042.gml" "E:\33_Mölndal\Nytt_20211007_3\00_Individual\4224.gml" "E:\33_Mölndal\Nytt_20211007_3\00_Individual\4328.gml" "E:\33_Mölndal\Nytt_20211007_3\00_Individual\4511.gml" "E:\33_Mölndal\Nytt_20211007_3\00_Individual\4617.gml" "E:\33_Mölndal\Nytt_20211007_3\00_Individual\4735.gml" "E:\33_Mölndal\Nytt_20211007_3\00_Individual\4800.gml" "E:\33_Mölndal\Nytt_20211007_3\00_Individual\4871.gml" "E:\33_Mölndal\Nytt_20211007_3\00_Individual\4950.gml" "E:\33_Mölndal\Nytt_20211007_3\00_Individual\4951.gml" "E:\33_Mölndal\Nytt_20211007_3\00_Individual\5562.gml" "E:\33_Mölndal\Nytt_20211007_3\00_Individual\5657.gml" "E:\33_Mölndal\Nytt_20211007_3\00_Individual\5877.gml" "E:\33_Mölndal\Nytt_20211007_3\00_Individual\5899.gml" "E:\33_Mölndal\Nytt_20211007_3\00_Individual\6162.gml" "E:\33_Mölndal\Nytt_20211007_3\00_Individual\6722.gml" "E:\33_Mölndal\Nytt_20211007_3\00_Individual\6919.gml" "E:\33_Mölndal\Nytt_20211007_3\00_Individual\6934.gml" "E:\33_Mölndal\Nytt_20211007_3\00_Individual\7062.gml" "E:\33_Mölndal\Nytt_20211007_3\00_Individual\7378.gml" "E:\33_Mölndal\Nytt_20211007_3\00_Individual\7716.gml" "E:\33_Mölndal\Nytt_20211007_3\00_Individual\7731.gml" "E:\33_Mölndal\Nytt_20211007_3\00_Individual\7965.gml" "E:\33_Mölndal\Nytt_20211007_3\00_Individual\8157.gml" "E:\33_Mölndal\Nytt_20211007_3\00_Individual\8617.gml" "E:\33_Mölndal\Nytt_20211007_3\00_Individual\8991.gml" "E:\33_Mölndal\Nytt_20211007_3\00_Individual\9586.gml" "E:\33_Mölndal\Nytt_20211007_3\00_Individual\9621.gml" "E:\33_Mölndal\Nytt_20211007_3\00_Individual\9823.gml" "E:\33_Mölndal\Nytt_20211007_3\00_Individual\9946.gml" "E:\33_Mölndal\Nytt_20211007_3\00_Individual\10282.gml" "E:\33_Mölndal\Nytt_20211007_3\00_Individual\10570.gml" "E:\33_Mölndal\Nytt_20211007_3\00_Individual\11003.gml" "E:\33_Mölndal\Nytt_20211007_3\00_Individual\11203.gml" "E:\33_Mölndal\Nytt_20211007_3\00_Individual\11611.gml" "E:\33_Mölndal\Nytt_20211007_3\00_Individual\11697.gml" "E:\33_Mölndal\Nytt_20211007_3\00_Individual\11752.gml" "E:\33_Mölndal\Nytt_20211007_3\00_Individual\11774.gml" "E:\33_Mölndal\Nytt_20211007_3\00_Individual\11776.gml" "E:\33_Mölndal\Nytt_20211007_3\00_Individual\11913.gml" "E:\33_Mölndal\Nytt_20211007_3\00_Individual\11989.gml" "E:\33_Mölndal\Nytt_20211007_3\00_Individual\12170.gml" "E:\33_Mölndal\Nytt_20211007_3\00_Individual\12206.gml" "E:\33_Mölndal\Nytt_20211007_3\00_Individual\12301.gml" "E:\33_Mölndal\Nytt_20211007_3\00_Individual\12382.gml" "E:\33_Mölndal\Nytt_20211007_3\00_Individual\12593.gml" "E:\33_Mölndal\Nytt_20211007_3\00_Individual\12990.gml" "E:\33_Mölndal\Nytt_20211007_3\00_Individual\13128.gml" "E:\33_Mölndal\Nytt_20211007_3\00_Individual\13472.gml" "E:\33_Mölndal\Nytt_20211007_3\00_Individual\14082.gml" "E:\33_Mölndal\Nytt_20211007_3\00_Individual\14085.gml" "E:\33_Mölndal\Nytt_20211007_3\00_Individual\14458.gml" "E:\33_Mölndal\Nytt_20211007_3\00_Individual\14520.gml" "E:\33_Mölndal\Nytt_20211007_3\00_Individual\15022.gml" "E:\33_Mölndal\Nytt_20211007_3\00_Individual\15065.gml" "E:\33_Mölndal\Nytt_20211007_3\00_Individual\15598.gml" "E:\33_Mölndal\Nytt_20211007_3\00_Individual\15690.gml" "E:\33_Mölndal\Nytt_20211007_3\00_Individual\15696.gml" "E:\33_Mölndal\Nytt_20211007_3\00_Individual\15709.gml" "E:\33_Mölndal\Nytt_20211007_3\00_Individual\15935.gml" "E:\33_Mölndal\Nytt_20211007_3\00_Individual\16098.gml" "E:\33_Mölndal\Nytt_20211007_3\00_Individual\16190.gml" "E:\33_Mölndal\Nytt_20211007_3\00_Individual\16484.gml" "E:\33_Mölndal\Nytt_20211007_3\00_Individual\16577.gml" "E:\33_Mölndal\Nytt_20211007_3\00_Individual\16749.gml" "E:\33_Mölndal\Nytt_20211007_3\00_Individual\16813.gml" "E:\33_Mölndal\Nytt_20211007_3\00_Individual\16922.gml" "E:\33_Mölndal\Nytt_20211007_3\00_Individual\16974.gml" "E:\33_Mölndal\Nytt_20211007_3\00_Individual\17120.gml" "E:\33_Mölndal\Nytt_20211007_3\00_Individual\17135.gml" "E:\33_Mölndal\Nytt_20211007_3\00_Individual\17387.gml" "E:\33_Mölndal\Nytt_20211007_3\00_Individual\17584.gml" "E:\33_Mölndal\Nytt_20211007_3\00_Individual\17651.gml" "E:\33_Mölndal\Nytt_20211007_3\00_Individual\17733.gml" "E:\33_Mölndal\Nytt_20211007_3\00_Individual\17950.gml" "E:\33_Mölndal\Nytt_20211007_3\00_Individual\17988.gml" "E:\33_Mölndal\Nytt_20211007_3\00_Individual\18002.gml" "E:\33_Mölndal\Nytt_20211007_3\00_Individual\18066.gml" "E:\33_Mölndal\Nytt_20211007_3\00_Individual\18131.gml" "E:\33_Mölndal\Nytt_20211007_3\00_Individual\18156.gml" "E:\33_Mölndal\Nytt_20211007_3\00_Individual\18221.gml" "E:\33_Mölndal\Nytt_20211007_3\00_Individual\18286.gml" "E:\33_Mölndal\Nytt_20211007_3\00_Individual\18299.gml" "E:\33_Mölndal\Nytt_20211007_3\00_Individual\18335.gml" "E:\33_Mölndal\Nytt_20211007_3\00_Individual\18499.gml" "E:\33_Mölndal\Nytt_20211007_3\00_Individual\18542.gml" "E:\33_Mölndal\Nytt_20211007_3\00_Individual\18861.gml" "E:\33_Mölndal\Nytt_20211007_3\00_Individual\19178.gml" "E:\33_Mölndal\Nytt_20211007_3\00_Individual\19502.gml" "E:\33_Mölndal\Nytt_20211007_3\00_Individual\19539.gml" "E:\33_Mölndal\Nytt_20211007_3\00_Individual\19786.gml" "E:\33_Mölndal\Nytt_20211007_3\00_Individual\19925.gml" "E:\33_Mölndal\Nytt_20211007_3\00_Individual\20105.gml" "E:\33_Mölndal\Nytt_20211007_3\00_Individual\20403.gml" "E:\33_Mölndal\Nytt_20211007_3\00_Individual\20494.gml" "E:\33_Mölndal\Nytt_20211007_3\00_Individual\20947.gml" "E:\33_Mölndal\Nytt_20211007_3\00_Individual\21245.gml" "E:\33_Mölndal\Nytt_20211007_3\00_Individual\21343.gml" "E:\33_Mölndal\Nytt_20211007_3\00_Individual\21613.gml" "E:\33_Mölndal\Nytt_20211007_3\00_Individual\21664.gml" "E:\33_Mölndal\Nytt_20211007_3\00_Individual\22534.gml" "E:\33_Mölndal\Nytt_20211007_3\00_Individual\22564.gml" "E:\33_Mölndal\Nytt_20211007_3\00_Individual\22577.gml" "E:\33_Mölndal\Nytt_20211007_3\00_Individual\22892.gml" "E:\33_Mölndal\Nytt_20211007_3\00_Individual\23022.gml" "E:\33_Mölndal\Nytt_20211007_3\00_Individual\23281.gml" "E:\33_Mölndal\Nytt_20211007_3\00_Individual\23444.gml" "E:\33_Mölndal\Nytt_20211007_3\00_Individual\23471.gml" "E:\33_Mölndal\Nytt_20211007_3\00_Individual\23527.gml" "E:\33_Mölndal\Nytt_20211007_3\00_Individual\999001.gml""   # Source CityGML File(s)
- DestDataset_CITYGML = E:\33_Mölndal\Leverans\Nytt\isolated2.gml   # Destination CityGML Document
- SourceDataset_SHAPEFILE = E:\33_Mölndal\Footprint_Customer\BAL_byggnad_y.shp   # Source Esri Shapefile(s)
- FEATURE_TYPES =

Readers:
- CITYGML_1: CITYGML from $(SourceDataset_CITYGML) in EPSG:3007
- SHAPEFILE_1: SHAPEFILE from $(SourceDataset_SHAPEFILE)

Writers:
- CITYGML_2: CITYGML to $(DestDataset_CITYGML)

BAL_byggnad_y (reader SHAPEFILE_1)
    attributes: td_id number(11,0), td_skapad_ char(200), td_skapa00 char(21), td_andrad_ char(200), td_andra00 char(21), bal_objekt char(36), bal_obje00 char(24), bal_obje01 number(11,0), bal_husnum number(11,0), bal_nybygg number(11,0), bal_undant char(3), bal_huvudb char(3), bal_tillby number(11,0), bal_ofri_g char(3), bal_byggna char(3), bal_andama char(254), bal_namn char(254), bal_anmark char(254), bal_ligger char(36), bal_tillho char(36), bal_berors char(254), bal_insaml char(20), bal_koordi char(15), bal_utvard char(25), bal_statis char(25), bal_vardep float, bal_vardee char(15), bal_koor00 char(15), bal_utva00 char(25), bal_stat00 char(25),
      bal_vardeh float, bal_vard00 char(15), td_synkdat char(21), sg_byggnad char(50), sg_byggn00 float, sg_tak_hog float, sg_takkant float, sg_takka00 float, sg_takka01 float, sg_takfot_ float, sg_takfo00 float, sg_takfo01 float, sg_generel float, sg_lagsta_ float, sg_entreni float, sg_fardigt float, sg_sockelh float, sg_husgrun float, sg_byggn01 float, sg_fiktivt float, td_area double, td_bal_ver char(250), td_bal_v00 char(250), td_noterin char(254), td_noter00 number(11,0), td_noter01 double, td_bygg_ar char(50), ge_matmeto char(250), ge_matme00 char(250), ge_lagesos float,
      ge_lages00 float, td_huvudan char(50)
    -> AttributeManager

Bookmark: CityGML_HxMAP
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> Counter
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> RoofSurface (writer CITYGML_2)
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> GroundSurface (writer CITYGML_2)
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> CityModel (writer CITYGML_2)
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
    -> BuildingPart (writer CITYGML_2)
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
    -> FeatureJoiner [LEFT]

Bookmark: Walls->Roofs
Counter
    CNT_ATTR = _WID
    DOMAIN = counter
    SCOPE = Global
    START = 0
    -> 2DForcer
    -> FeatureJoiner_3 [LEFT]
2DForcer
    2D -> AreaCalculator
AreaCalculator
    AREA_ATTR = _a1
    AREA_TYPE = Plane Area
    MULT = 1
    -> Tester
Tester
    BOOL_OP = OR
    COMPOSITE_TEST = 1
    TEST_CLAUSE = TEST @Value(_a1) > 0.1
    TEST_MODE = TEST
    PASSED -> AttributeManager_2
AttributeManager_2
    ATTR_TABLE = SET_TO fme_feature_type = RoofSurface
    -> FeatureJoiner_3 [RIGHT]
FeatureJoiner_3
    ATTR_CONFLICT_RES = Use Right
    GEOMETRY_HANDLING = Use Left
    JOIN_KEYS = _WID _WID AUTO
    JOIN_MODE = Inner
    JOINED -> AttributeManager_3
    UNJOINED_LEFT -> AttributeManager_4
AttributeManager_3
    ATTR_TABLE:
      REMOVE _WID
      REMOVE _a1
    -> RoofSurface (writer CITYGML_2)
AttributeManager_4
    ATTR_TABLE = REMOVE _WID
    -> WallSurface (writer CITYGML_2)

Bookmark: Writer Feature Types
WallSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
RoofSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
GroundSurface (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
CityModel (writer CITYGML_2)
    attributes: citygml_target_uri xml_buffer, gml_description xml_buffer, gml_name xml_buffer, citygml_city_object_member{}.xlink_href xml_buffer, citygml_appearance_member{}.xlink_href xml_buffer, gml_feature_member{}.xlink_href xml_buffer
BuildingPart (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer
Building (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, td_id xml_int64, bal_objekt xml_char(36)

Bookmark: Assign Attributes from Footprints
AttributeManager
    ATTR_TABLE:
      REMOVE td_skapad_
      REMOVE td_skapa00
      REMOVE td_andrad_
      REMOVE td_andra00
      REMOVE bal_obje00
      REMOVE bal_obje01
      REMOVE bal_husnum
      REMOVE bal_nybygg
      REMOVE bal_undant
      REMOVE bal_huvudb
      REMOVE bal_tillby
      REMOVE bal_ofri_g
      REMOVE bal_byggna
      REMOVE bal_andama
      REMOVE bal_namn
      REMOVE bal_anmark
      REMOVE bal_ligger
      REMOVE bal_tillho
      REMOVE bal_berors
      REMOVE bal_insaml
      REMOVE bal_koordi
      REMOVE bal_utvard
      REMOVE bal_statis
      REMOVE bal_vardep
      REMOVE bal_vardee
      REMOVE bal_koor00
      REMOVE bal_utva00
      REMOVE bal_stat00
      REMOVE bal_vardeh
      REMOVE bal_vard00
      REMOVE td_synkdat
      REMOVE sg_byggnad
      REMOVE sg_byggn00
      REMOVE sg_tak_hog
      REMOVE sg_takkant
      REMOVE sg_takka00
      REMOVE sg_takka01
      REMOVE sg_takfot_
      REMOVE sg_takfo00
      REMOVE sg_takfo01
      REMOVE sg_generel
      REMOVE sg_lagsta_
      REMOVE sg_entreni
      REMOVE sg_fardigt
      REMOVE sg_sockelh
      REMOVE sg_husgrun
      REMOVE sg_byggn01
      REMOVE sg_fiktivt
      REMOVE td_area
      REMOVE td_bal_ver
      REMOVE td_bal_v00
      REMOVE td_noterin
      REMOVE td_noter00
      REMOVE td_noter01
      REMOVE td_bygg_ar
      REMOVE ge_matmeto
      REMOVE ge_matme00
      REMOVE ge_lagesos
      REMOVE ge_lages00
      REMOVE td_huvudan
      REMOVE fme_feature_type
    -> FeatureJoiner [RIGHT]
FeatureJoiner
    ATTR_CONFLICT_RES = Use Left
    GEOMETRY_HANDLING = Use Left
    JOIN_KEYS = gml_name td_id AUTO
    JOIN_MODE = Inner
    JOINED -> Building (writer CITYGML_2)
    UNJOINED_LEFT -> Building (writer CITYGML_2)
