FME workspace FANOUT_points.fmw

Parameters:
- SourceDataset_SHAPEFILE = D:\02_Pilot\Vienna subway\ClientFeedback\Feedback delviery\UG\Vienna_point.shp   # Source Esri Shapefile(s)
- FEATURE_TYPES = Vienna_point
- DestDataset_SHAPEFILE = D:\02_Pilot\Vienna subway\ClientFeedback\Feedback delviery\UG\Fanout   # Destination Esri Shapefile Folder

Readers:
- SHAPEFILE_1: SHAPEFILE from $(SourceDataset_SHAPEFILE)

Writers:
- SHAPEFILE_2: SHAPEFILE to $(DestDataset_SHAPEFILE) in EPSG:31256

Vienna_point (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> Vienna_point (writer SHAPEFILE_2)
Vienna_point (writer SHAPEFILE_2)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
