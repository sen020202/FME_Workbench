FME workspace -Derivaties-Hydro_vector_Flatten_Ver-01.fmw

Parameters:
- SourceDataset_DGNV8 = H:\Exchange\MEKS\water.dgn   # Source Bentley MicroStation Design File(s)
- FEATURE_TYPES = Contour Island Water
- DestDataset_DGNV8 = H:\Exchange\MEKS\water_Errorr_FME.dgn   # Destination Bentley MicroStation Design File

Readers:
- DGNV8_1: DGNV8 from $(SourceDataset_DGNV8)

Writers:
- DGNV8_2: DGNV8 to $(DestDataset_DGNV8)

AttributeFilter
    ATTR_NAME = igds_level_name
    ATTR_VALUES = <Empty>,<Missing>,<Null>,<Unfiltered>,Water,Island,Contour
    Water -> AreaBuilder
    Water -> LineOnAreaOverlayer_3 [AREA]
    Island -> AreaBuilder
    Contour -> Counter
More-Length_issues: Inspector
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    AREA -> Tester_4
Tester_4
    BOOL_OP = OR
    COMPOSITE_TEST = 1
    TEST_CLAUSE = TEST @Value(igds_level_name) = Island
    TEST_MODE = TEST
    FAILED -> LineOnAreaOverlayer_2 [AREA]
    FAILED -> Counter_2
AttributeManager_4
    ATTR_TABLE = RENAME_SET_VALUE igds_level > igds_level_name = Err_Contour_nearby_70CMS_Less
    -> Level1 (writer DGNV8_2)
Counter_2
    CNT_ATTR = WATER_ID
    DOMAIN = counter
    SCOPE = Global
    START = 1
    -> AreaOnAreaOverlayer [AREA]
AttributeManager
    ATTR_TABLE = SET_TO igds_level_name = Err_Check_Water_polyons_Heights
    -> Level1 (writer DGNV8_2)
Level1 (writer DGNV8_2)

Bookmark: Input
Island (reader DGNV8_1)
    -> AttributeFilter

Bookmark: Creating the round contours with ID
Note: Creating the round contours with ID
Counter
    CNT_ATTR = CON_ID
    DOMAIN = counter
    SCOPE = Global
    START = 1
    -> LineOnAreaOverlayer_3 [LINE]
    -> GeometryCoercer
GeometryCoercer
    GQUERY:
      for $geom in //geometry
      where $geom/count(parent::geometry) = 0
      return number($geom/@fme_id)
    KIND = fme_polygon
    COERCED -> AreaBuilder_2
    UNTOUCHED -> LineOnAreaOverlayer_2 [LINE]

Bookmark: Water polygon height comparision
AreaBuilder_2
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    AREA -> AreaOnAreaOverlayer [AREA]
Note: Water polygon height comparision
AreaOnAreaOverlayer
    ACCUM_ATTRS_NAME = Merge Incoming Attributes
    CLEANING_TOLERANCE = 0.001
    CONNECT_Z_MODE = First Wins
    DEAGGREGATE_INPUT = Yes
    LIST_NAME = _1_
    OVC_ATTR = _overlaps
    AREA -> Tester
Tester
    BOOL_OP = OR
    COMPOSITE_TEST = 1 OR 2
    TEST_CLAUSE:
      TEST @Value(igds_level_name) = Water
      TEST @Value(igds_level_name) = Island
    TEST_MODE = TEST
    PASSED -> Tester_2
    FAILED -> AttributeCreator_5
Tester_2
    BOOL_OP = OR
    COMPOSITE_TEST = 1
    TEST_CLAUSE = TEST @Value(_overlaps) = 1
    TEST_MODE = TEST
    FAILED -> AttributeCreator_4
AttributeCreator_4
    ATTR_TABLE = SET_TO igds_level_name = Err_Check_Water_polyons_Heights
    -> AttributeManager
AttributeCreator_5
    ATTR_TABLE = SET_TO igds_level_name = Err_Check_Water_polyons_Heights
    -> AttributeManager

Bookmark: Contour_Crossing_Check-Errors
LineOnAreaOverlayer_3
    ATTR_ACCUM_MODE = Prefix Incoming
    CANDIDATE_LIST_ATTRS_TO_INCLUDE_MODE = All Attributes
    CANDIDATE_LIST_NAME = _33_
    CLEANING_TOLERANCE = 0.001
    DEAGGREGATE_INPUT = Yes
    INCOMING_PREFIX = _2_
    LIST_NAME = _22_
    OV_ATTR = 3_overlaps
    LINE -> Tester_6
Tester_6
    BOOL_OP = OR
    COMPOSITE_TEST = 1
    TEST_CLAUSE = TEST @Value(3_overlaps) = 1
    TEST_MODE = TEST
    PASSED -> StringConcatenator_2
    PASSED -> LengthCalculator
StringConcatenator_2
    ACTION = Create New Attribute
    PARM_LINE = fme_basicstring:14%1%23:@Value(CON_ID)_@Value(igds_element_id)
    VAL_ATTR = _result
    -> Matcher_2
Note: Contour_Crossing_Check-Errors
Matcher_2
    BLANK_AND_MISSING_DIFFER = No
    CHECK_TYPES_AND_ENCODINGS = No
    CNT_ATTR = _match_id
    MATCHATTRS = _result
    MATCH_STRATEGY = Match Selected Attributes
    MATCHED -> Contour_Crossing_Check-Errors
    MATCHED -> AttributeCreator_3
AttributeCreator_3
    ATTR_TABLE = SET_TO igds_level_name = Err_Contour_Twice_Cross
    -> AttributeManager_3
AttributeManager_3
    ATTR_TABLE:
      SET_TO igds_level_name = Err_Contour_Twice_Cross
      SET_TO igds_level = Err_Contour_Twice_Cross
    -> Level1 (writer DGNV8_2)
Contour_Crossing_Check-Errors: Inspector

Bookmark: Suspecious Length - findlings
Note: Suspecious Length - findings
LengthCalculator
    DIM = 2
    LEN_ATTR = _length
    MULT = 1
    -> Tester_7
    -> Tester_8
    -> Counter_3
Counter_3
    CNT_ATTR = LINE_BUILD_ID
    DOMAIN = counter
    SCOPE = Global
    START = 1
    -> Extract_End_Points [Input_Features]
Extract_End_Points: Extract End Points
    Buffer = 0
    BufferUnit = Feet
    ExtractGeometry = Yes
    Point_Output -> LineBuilder
LineBuilder
    ACCUM_INPUT_ATTRS = Use Attributes From One Feature
    GROUP_BY = LINE_BUILD_ID
    REMOVE_DUPLICATES = No
    LINE -> LengthCalculator_2
LengthCalculator_2
    DIM = 2
    LEN_ATTR = New_Len_1
    MULT = 1
    -> AttributeCreator
AttributeCreator
    ATTR_TABLE = SET_TO Diff = @Evaluate(@div(@Value(_length),@Value(New_Len_1)))
    -> Tester_9
Tester_9
    BOOL_OP = OR
    COMPOSITE_TEST = 1
    TEST_CLAUSE = TEST @Value(Diff) <= 1.2
    TEST_MODE = TEST
    FAILED -> More-Length_issues
    FAILED -> AttributeCreator_2
Tester_7
    BOOL_OP = OR
    COMPOSITE_TEST = 1
    TEST_CLAUSE = TEST @Value(_length) <= 40
    TEST_MODE = TEST
    FAILED -> Junction
Tester_8
    BOOL_OP = OR
    COMPOSITE_TEST = 1
    TEST_CLAUSE = TEST @Value(_length) >= 1
    TEST_MODE = TEST
    FAILED -> Junction
    FAILED -> AttributeCreator_7
Junction
    -> More-40___less-lengh1
    -> AttributeCreator_2
AttributeCreator_2
    ATTR_TABLE = SET_TO igds_level_name = Err_Check_Suspect_Lengths
    -> AttributeManager_2
AttributeManager_2
    ATTR_TABLE:
      SET_TO igds_level_name = Err_Check_Suspect_Lengths
      SET_TO igds_level = Err_Check_Suspect_Lengths
    -> Level1 (writer DGNV8_2)
More-40___less-lengh1: Inspector
AttributeCreator_7
    ATTR_TABLE = SET_TO igds_level_name = Err_Check_Small_size_Con
    -> AttributeManager_5
AttributeManager_5
    ATTR_TABLE:
      SET_TO igds_level_name = Err_Check_Small_size_Con
      SET_TO igds_level = Err_Check_Small_size_Con
    -> Level1 (writer DGNV8_2)

Bookmark: Too close contours - findling
LineOnAreaOverlayer_2
    CANDIDATE_LIST_ATTRS_TO_INCLUDE = CON_ID
    CANDIDATE_LIST_ATTRS_TO_INCLUDE_MODE = Selected Attributes
    CANDIDATE_LIST_NAME = _AN
    CLEANING_TOLERANCE = 0.001
    DEAGGREGATE_INPUT = Yes
    OV_ATTR = _overlaps
    LINE -> Tester_3
Tester_3
    BOOL_OP = OR
    COMPOSITE_TEST = 1
    TEST_CLAUSE = TEST @Value(_overlaps) = 0
    TEST_MODE = TEST
    FAILED -> LineOnLineOverlayer [LINE]
LineOnLineOverlayer
    ATTRS_ACCUM_MODE = Use Attributes From One Feature
    CLEANING_TOLERANCE = 0.7
    DEAGGREGATE_INPUT = Yes
    GENERATE_LIST_DROP = NO
    OV_ATTR = L_overlaps
    SEPARATE_COLLINEAR_SEGMENTS = No
    LINE -> Tester_5
Tester_5
    BOOL_OP = OR
    COMPOSITE_TEST = 1
    TEST_CLAUSE = TEST @Value(L_overlaps) = 1
    TEST_MODE = TEST
    FAILED -> AttributeCreator_6
Note: Too close contours - findling
AttributeCreator_6
    ATTR_TABLE = SET_TO igds_level_name = Err_Contour_Line_too_Close
    -> AttributeManager_4
