FME workspace polygonCreation.fmw

Parameters:
- SourceDataset_DGNV8 = D:\Temp\iceberg\for_polygon.dgn   # Source Bentley MicroStation Design File(s)
- FEATURE_TYPES = EB EB_P EG EG_P GRD GRD_P KB KI N0 RAIL RSHD RSHD_P SILO WTANK BLD Default
- DestDataset_DGNV8 = D:\Temp\iceberg\for_polygon_ERRor_Lines.dgn   # Destination Bentley MicroStation Design File
- DestDataset_SHAPEFILE = D:\Temp\iceberg\sHP   # Destination Esri Shapefile Folder

Readers:
- DGNV8_1: DGNV8 from $(SourceDataset_DGNV8)

Writers:
- DGNV8_2: DGNV8 to $(DestDataset_DGNV8)
- SHAPEFILE_1: SHAPEFILE to $(DestDataset_SHAPEFILE)

BLD (reader DGNV8_1)
    -> FeatureHolder
FeatureHolder
    -> Intersector
Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> GeometryFilter
    COLLAPSED -> GeometryFilter
    <REJECTED> -> GeometryFilter
GeometryFilter
    FILTER_MODE = SIMPLE
    FILTER_MULTI = FILTER_TYPES]"Point Line Area"]FME_CONTROLLER_QUERY_FILE]]FME_CONTROLLER_CHOICE]Simple
    <UNFILTERED> -> GeometryCoercer
    Point -> PointOnAreaOverlayer [POINT]
    Point -> Counter
    Curve -> AreaBuilder
    Area -> AreaBuilder
Counter
    CNT_ATTR = _count
    DOMAIN = counter
    SCOPE = Global
    START = 0
    -> AreaBuilder
GeometryCoercer
    GQUERY:
      for $geom in //geometry
      where $geom/count(parent::geometry) = 0
      return number($geom/@fme_id)
    KIND = fme_line
    COERCED -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    AREA -> AttributeRemover
    Incomplete -> AttributeCreator
AttributeCreator
    ATTR_TABLE = SET_TO igds_level_name (buffer) = __Error_Dangles
    -> DGNStyler
DGNStyler
    COLOR_BY_LEVEL_DISPLAY = No
    COLOR_CHOICE_DISPLAY = RGB
    LINE_STYLE = 0
    LINE_WEIGHT = 7
    RGB_COLOR = 1,1,1
    RGB_FILL_COLOR = 1,1,1
    DGNStyled -> BLD (writer DGNV8_2)
AttributeRemover
    REMOVE_ATTRS = fme_feature_type,fme_rejection_code,igds_level_name
    -> PointOnAreaOverlayer [AREA]
PointOnAreaOverlayer
    ATTR_ACCUM_MODE = Merge Incoming
    ATTR_CONFLICT_RES = Use Original
    DEAGGREGATE_INPUT = Yes
    OV_ATTR = _overlaps
    POLYS_FIRST = NO
    AREA -> AttributeFilter
    AREA -> AttributeExposer
AttributeExposer
    ATTR_LIST = fme_basename,igds_level
    -> AreaCalculator
AreaCalculator
    AREA_ATTR = _area
    AREA_TYPE = Plane Area
    MULT = 1
    -> AttributeCreator_5
AttributeCreator_5
    ATTR_TABLE = SET_TO Polygon_Area (real64) = @Value(_area)
    -> Reprojector
Reprojector
    DEST = EPSG:7850
    INTERPOLATION_TYPE_NAME = Nearest Neighbor
    RASTER_CELL_SIZE = Preserve Cells
    RASTER_TOLERANCE = 0.0
    REPROJECTED -> BLD (writer SHAPEFILE_1)
BLD (writer SHAPEFILE_1)
    attributes: igds_level varchar(80)
AttributeFilter
    ATTR_NAME = _overlaps
    ATTR_VALUES = <Empty>,<Missing>,<Null>,<Unfiltered>,0,1
    <UNFILTERED> -> AttributeCreator_2
    0 -> AttributeCreator_3
    1 -> AttributeCreator_4
AttributeCreator_2
    ATTR_TABLE = SET_TO igds_level_name (buffer) = __MultiPoint_Polygon_
    -> BLD (writer DGNV8_2)
AttributeCreator_3
    ATTR_TABLE = SET_TO igds_level_name (buffer) = __SinglePoint_Polygons
    -> BLD (writer DGNV8_2)
AttributeCreator_4
    ATTR_TABLE = SET_TO igds_level_name (buffer) = __SinglePoint_Polygons
    -> BLD (writer DGNV8_2)
BLD (writer DGNV8_2)
