FME workspace reprojecct.fmw

Parameters:
- SourceDataset_SHAPEFILE = D:\02_Pilot\Vienna subway\ViennaSubway\Delivery\Merge\strasse\strasse_linear.shp   # Source Esri Shapefile(s)
- FEATURE_TYPES = strasse_linear
- DestDataset_SHAPEFILE = D:\02_Pilot\Vienna subway\ViennaSubway\Delivery\Merge\Reprojected   # Destination Esri Shapefile Folder
- SourceDataset_SHAPEFILE_2 = D:\02_Pilot\Vienna subway\ViennaSubway\Delivery\Merge\strasse\strasse_point.shp   # Source Esri Shapefile(s)
- DestDataset_SHAPEFILE_3 = D:\02_Pilot\Vienna subway\ViennaSubway\Delivery\Merge\Reprojected   # Destination Esri Shapefile Folder

Readers:
- SHAPEFILE_1: SHAPEFILE from $(SourceDataset_SHAPEFILE)
- SHAPEFILE_3: SHAPEFILE from $(SourceDataset_SHAPEFILE_2)

Writers:
- SHAPEFILE_2: SHAPEFILE to $(DestDataset_SHAPEFILE)
- SHAPEFILE_4: SHAPEFILE to $(DestDataset_SHAPEFILE_3)

UG_linear (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> Reprojector
Reprojector
    DEST = EPSG:31256
    INTERPOLATION_TYPE_NAME = Nearest Neighbor
    RASTER_CELL_SIZE = Preserve Cells
    RASTER_TOLERANCE = 0.0
    SOURCE = EPSG:3035
    REPROJECTED -> strasse_linear (writer SHAPEFILE_2)
strasse_linear (writer SHAPEFILE_2)
    attributes: THEMATIK varchar(50), RTRTYP long, ANGLE long, DETAILS varchar(255), BETREIBER varchar(50), MATERIAL varchar(50), ANZAHL short, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
Luftungszentrale_Notausgang_point (reader SHAPEFILE_3)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> Reprojector_2
Reprojector_2
    DEST = EPSG:31256
    INTERPOLATION_TYPE_NAME = Nearest Neighbor
    RASTER_CELL_SIZE = Preserve Cells
    RASTER_TOLERANCE = 0.0
    SOURCE = EPSG:3035
    REPROJECTED -> strasse_point (writer SHAPEFILE_4)
strasse_point (writer SHAPEFILE_4)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
