FME workspace _Correction_generale_V6.fmw

Parameters:
- Choix_lot = 13   # Name of lot to control
- SourceDataset_ACAD = J:\Pessac\MMS\4-Procedures\07-ROUTINE FME\3-EXPLOITATION\BM_PCRS\Echantillons_BX_PCRS\Differents_PL_avec_et_sans_TP.dwg   # DWG data to transform
- FEATURE_TYPES = 0 CR~LEVER~P~LEVE CR~LEVER~P~PONCTUEL INFRA~ROU~BORD~BAS INFRA~ROU~BORD~HAUT INFRA~ROU~SOL~- MOB~PROT~ARC~PROT MOB~PUB~SUP~PORT MOB~PUB~SUP~POTEN MOB~PUB~SUP~REC RESEAU~00~POT~PORT RESEAU~00~POT~POTEN RESEAU~ASSA~AVA~D RESEAU~ASSA~GRIL~REC RESEAU~COM~SUP~REN_O RESEAU~SLT~POT_TRI~PORT RESEAU~SLT~POT_TRI~POTEN SIGN~V~PORT~- SIGN~V~POT_FER~PORT SIGN~V~POT_FER~POTEN SIGN~V~POT_JAL~ITI_PORT SIGN~V~POT_JAL~LOC_PORT SIGN~V~POT_JAL~PUB_PORT SIGN~V~POT_ROU~PORT SIGN~V~POT_ROU~POTEN
- GO_sortie_erreurs = Yes   # Produce error report for checking?
- Sortie_Dossier = J:\Pessac\MMS\4-Procedures\07-ROUTINE FME\3-EXPLOITATION\BM_PCRS\Echantillons_BX_PCRS\correction   # Output directory
- FEATURE_TYPES_2 = DELIM~CLOT~PIL~CAR MOB~URB~BANC~- NATURE~VERT~BAC~REC RESEAU~00~ARM~00 RESEAU~00~ARM~ENCA RESEAU~00~COF~00 RESEAU~00~COF~ENCA RESEAU~00~PLA~CAR RESEAU~00~PLA~REC RESEAU~00~REG~CAR RESEAU~00~REG~REC RESEAU~ASSA~AVA~00 RESEAU~ASSA~AVA~D RESEAU~ASSA~AVA~G RESEAU~ASSA~AVA~GRILLE RESEAU~ASSA~AVA~RE_GR RESEAU~ASSA~AVA~REGARD RESEAU~ASSA~GRIL~REC RESEAU~ASSA~REG~CAR RESEAU~CHAU~ARM~00 RESEAU~CHAU~ARM~ENCA RESEAU~CHAU~COF~00 RESEAU~CHAU~COF~ENCA RESEAU~CHAU~PLA~CAR RESEAU~CHAU~PLA~REC RESEAU~CHAU~REG~CAR RESEAU~CHAU~REG~REC RESEAU~COM~COF~00 RESEAU~COM~COF~ENCA RESEAU~COM~PLA~CAR RESEAU~COM~PLA~REC RESEAU~ECL~ARM~00 RESEAU~ECL~ARM~ENCA RESEAU~ECL~COF~00 RESEAU~ECL~COF~ENCA RESEAU~ECL~PLA~CAR RESEAU~ECL~PLA~REC RESEAU~ELEC~ARM~00 RESEAU~ELEC~ARM~ENCA RESEAU~ELEC~COF~00 RESEAU~ELEC~COF~ENCA RESEAU~ELEC~PLA~CAR RESEAU~ELEC~PLA~REC RESEAU~GAZ~ARM~00 RESEAU~GAZ~ARM~ENCA RESEAU~GAZ~COF~00 RESEAU~GAZ~COF~ENCA RESEAU~GAZ~PLA~CAR RESEAU~GAZ~PLA~REC RESEAU~GAZ~REG~CAR RESEAU~GAZ~REG~REC RESEAU~INOLIA~PLA~CAR RESEAU~INOLIA~PLA~REC RESEAU~SLT~PLA~CAR RESEAU~SLT~PLA~REC DELIM~CLOT~PIL~REC   # Feature Types to Read (blocs explo)

Readers:
- ACAD_1: ACAD from $(SourceDataset_ACAD) in EPSG:3945
- ACAD_2: ACAD from $(SourceDataset_ACAD) in EPSG:3945

Writers:
- ACAD_3: ACAD to $(Sortie_Dossier) in EPSG:3945
- XLSXW_1: XLSXW to $(Sortie_Dossier)
- ACAD_4: ACAD to $(Sortie_Dossier) in EPSG:3945

AttributeRemover
    REMOVE_ATTRS = _distance,Coord_Z,_IDOriginal_PAR,STOP,_element_index,_IDOriginal_TL,_closest_candidate_x,Round_z_Anchor,_candidate_angle,_x_Anchor,angle,closest_candidate_x,candidate_angle,closest_candidate_y,IDENT_LIN,_z_Anchor,Coord_X,Coord_Y,_closest_base_x,_y_Anchor,_closest_candidate_y,_angle,_remnant,_IDOriginal,_candidate_label_angle,IDENT_index,IDENT_PAR,candidate_label_angle,_index,distance,Round_Coord_Z,_closest_base_y,_IDOriginal_lineaire,closest_base_x,closest_base_y
    -> Counter_3
AttributeKeeper_17 [off]
    KEEP_ATTRS = autocad_block_name,autocad_elevation,fme_feature_type,autocad_rotation,autocad_zscale,autocad_source_filename,_filename,autocad_entity,FORME,MAT,TYPE,autocad_xscale,autocad_yscale,autocad_layer,ALT

Bookmark: Entrée
RESEAU~SLT~BOUCLE~FEU (reader ACAD_1)
    attributes: ALT char(1), TYPE char(5), MAT char(4)
    -> Junction_117
    -> FilenamePartExtractor
FilenamePartExtractor
    FULLNAME_ATTR = _filename
    SRC_ATTR = @Value(autocad_source_filename)
    -> Counter_5
Note: _IDOriginal
Counter_5
    CNT_ATTR = _IDOriginal
    DOMAIN = IDOriginal
    SCOPE = Global
    START = 0
    -> AttributeSplitter
Note: REC avec xscale=yscale considérés comme SSCLASSE:CAR
AttributeCreator_121
    ATTR_TABLE:
      SET_TO SSCLASSE = FME_CONDITIONAL:DEFAULT_VALUE'_FME_NO_OP_'BOOL_OP;AND;COMPOSITE_TEST;1 AND 2;TEST @Value(SSCLASSE) = REC;TEST @Value(autocad_xscale) = @Value(autocad_yscale)'CAR'FME_NUM_CONDITIONS2___
      SET_TO fme_feature_type_original = @Value(fme_feature_type)
    -> AttributeCreator_122
AttributeCreator_122
    ATTR_TABLE:
      SET_TO fme_feature_type = @Value(THEME)~@Value(SSTHEME)~@Value(CLASSE)~@Value(SSCLASSE)
      SET_TO autocad_layer = @Value(THEME)~@Value(SSTHEME)~@Value(CLASSE)~@Value(SSCLASSE)
    -> AttributeFilter_3
Note: GO=Yes
Tester_91
    BOOL_OP = OR
    TEST_CLAUSE = TEST No = Yes
    TEST_MODE = TEST
    PASSED -> Junction_112
Note: vers vérif. sens des / polylignes: lignes 90°
Junction_112
Note: vers chrono
Junction_117
    -> Junction_118

Bookmark: Mise en forme
AttributeSplitter
    ATTR_NAME = autocad_layer
    DELIMITER = ~
    DROP_EMPTY_PARTS = No
    LIST_NAME = _description
    TRIM_OPTION = Both
    -> AttributeCreator
AttributeCreator
    ATTR_TABLE:
      SET_TO THEME = @Value(_description{0})
      SET_TO SSTHEME = @Value(_description{1})
      SET_TO CLASSE = @Value(_description{2})
      SET_TO SSCLASSE = @Value(_description{3})
    -> Tester_40
    -> Tester_91
Tester_40
    BOOL_OP = OR
    TEST_CLAUSE = TEST autocad_xscale ATTRIBUTE_HAS_A_VALUE ""
    TEST_MODE = TEST
    PASSED -> AttributeCreator_37
    FAILED -> AttributeFilter_3
AttributeCreator_37
    ATTR_TABLE:
      SET_TO autocad_xscale_2 = @Evaluate(@abs(@Value(autocad_xscale)))
      SET_TO autocad_yscale_2 = @Evaluate(@abs(@Value(autocad_yscale)))
    -> AttributeRounder
AttributeRounder
    PLACES = 2
    ROUND_TYPE = Nearest
    SRC_ATTRS = autocad_yscale_2 autocad_xscale_2
    -> AttributeCreator_121

Bookmark: Verification Calque
AttributeFilter_3
    ATTR_NAME = THEME
    ATTR_VALUES = <Empty>,<Missing>,<Null>,<Unfiltered>,DELIM,INFRA,NATURE,RESEAU,MOB,SIGN,HAB,CR,ERROR,Erreur,Alerte
    DELIM -> Tester_23
    INFRA -> Tester_12
    NATURE -> Tester_13
    RESEAU -> AttributeFilter_4
    MOB -> Tester_28
    SIGN -> Tester_27
    HAB -> Tester_26
    CR -> Tester_6
    ERROR -> Junction_129
Note: ERROR traitées vers sortie
Note: ERROR anciennes non prises en compte
Note: Calque "Annotation" pour permettre aux contrôleurs de garder une trace écrite sans générer d'erreur "Wrong Layer"?
Junction_129
    -> Junction_130

Bookmark: DELIM / Attribution FORME
Tester_23
    BOOL_OP = OR
    TEST_CLAUSE:
      TEST @Value(autocad_layer) = DELIM~BATI~FAC~LEG
      TEST @Value(autocad_layer) = DELIM~BATI~FAC~DUR
      TEST @Value(autocad_layer) = DELIM~BATI~PROE~PIED
      TEST @Value(autocad_layer) = DELIM~BATI~PROE~NEZ
      TEST @Value(autocad_layer) = DELIM~BATI~SUR~-
      TEST @Value(autocad_layer) = DELIM~CLOT~CLOT~PAD
      TEST @Value(autocad_layer) = DELIM~CLOT~CLOT~PALI
      TEST @Value(autocad_layer) = DELIM~CLOT~CLOT~SOC_O
      TEST @Value(autocad_layer) = DELIM~CLOT~CLOT~SOC_N
      TEST @Value(autocad_layer) = DELIM~CLOT~CLOT~TREI
      TEST @Value(autocad_layer) = DELIM~CLOT~MUR~BAHU_N
      TEST @Value(autocad_layer) = DELIM~CLOT~MUR~BAHU_O
      TEST @Value(autocad_layer) = DELIM~CLOT~MUR~ENRO
      TEST @Value(autocad_layer) = DELIM~CLOT~MUR~MUR
      TEST @Value(autocad_layer) = DELIM~CLOT~MUR~PARA
      TEST @Value(autocad_layer) = DELIM~CLOT~MUR~SOUT
      TEST @Value(autocad_layer) = DELIM~CLOT~CLOT~PAD_EP
      TEST @Value(autocad_layer) = DELIM~CLOT~CLOT~PALI_EP
      TEST @Value(autocad_layer) = DELIM~CLOT~CLOT~SOC_O_EP
      TEST @Value(autocad_layer) = DELIM~CLOT~CLOT~SOC_N_EP
      TEST @Value(autocad_layer) = DELIM~CLOT~CLOT~TREI_EP
      TEST @Value(autocad_layer) = DELIM~CLOT~MUR~BAHU_N_EP
      TEST @Value(autocad_layer) = DELIM~CLOT~MUR~BAHU_O_EP
      TEST @Value(autocad_layer) = DELIM~CLOT~MUR~ENRO_EP
      TEST @Value(autocad_layer) = DELIM~CLOT~MUR~MUR_EP
      TEST @Value(autocad_layer) = DELIM~CLOT~MUR~PARA_EP
      TEST @Value(autocad_layer) = DELIM~CLOT~MUR~SOUT_EP
      TEST @Value(autocad_layer) = DELIM~CLOT~PIL~CAR
      TEST @Value(autocad_layer) = DELIM~CLOT~PIL~CIR
      TEST @Value(autocad_layer) = DELIM~CLOT~PIL~OVA
      TEST @Value(autocad_layer) = DELIM~CLOT~PIL~REC
      TEST @Value(autocad_layer) = DELIM~DP~LIM~MAT_O
      TEST @Value(autocad_layer) = DELIM~DP~LIM~MAT_N
      TEST @Value(autocad_layer) = DELIM~DP~LIM~CAD
      TEST @Value(autocad_layer) = DELIM~DP~LIM~DEC
      TEST @Value(autocad_layer) = DELIM~DP~AMOR~-
      TEST @Value(autocad_layer) = DELIM~DP~PAR~-
      TEST @Value(autocad_layer) = DELIM~OUVRA~PONT~PILE
      TEST @Value(autocad_layer) = DELIM~OUVRA~PONT~TAB
      TEST @Value(autocad_layer) = DELIM~OUVRA~00~-
      TEST @Value(autocad_layer) = DELIM~SEUIL~-~PARK
      TEST @Value(autocad_layer) = DELIM~SEUIL~-~CAVE
      TEST @Value(autocad_layer) = DELIM~SEUIL~-~SOUP
      TEST @Value(autocad_layer) = DELIM~SEUIL~-~VITRI
      TEST @Value(autocad_layer) = DELIM~SEUIL~-~00
    TEST_MODE = TEST
    PASSED -> AttributeCreator_6
AttributeCreator_6
    ATTR_TABLE = SET_TO FORME = FME_CONDITIONAL:DEFAULT_VALUE'_FME_NO_OP_'BOOL_OP;OR;COMPOSITE_TEST;<Unused>;TEST @Value(autocad_layer) = DELIM~BATI~FAC~LEG;TEST @Value(autocad_layer) = DELIM~BATI~FAC~DUR;TEST @Value(autocad_layer) = DELIM~BATI~PROE~PIED;TEST @Value(autocad_layer) = DELIM~BATI~PROE~NEZ;TEST @Value(autocad_layer) = DELIM~BATI~SUR~-;TEST @Value(autocad_layer) = DELIM~CLOT~CLOT~PAD;TEST @Value(autocad_layer) = DELIM~CLOT~CLOT~PALI;TEST @Value(autocad_layer) = DELIM~CLOT~CLOT~SOC_O;TEST @Value(autocad_layer) = DELIM~CLOT~CLOT~SOC_N;TEST @Value(autocad_layer) = DELIM~CLOT~CLOT~TREI;TEST @Value(autocad_layer) = DELIM~CLOT~MUR~BAHU_N;TEST @Value(autocad_layer) = DELIM~CLOT~MUR~BAHU_O;TEST @Value(autocad_layer) = DELIM~CLOT~MUR~ENRO;TEST @Value(autocad_layer) = DELIM~CLOT~MUR~MUR;TEST @Value(autocad_layer) = DELIM~CLOT~MUR~PARA;TEST @Value(autocad_layer) = DELIM~CLOT~MUR~SOUT;TEST @Value(autocad_layer) = DELIM~DP~LIM~MAT_O;TEST @Value(autocad_layer) = DELIM~DP~LIM~MAT_N;TEST @Value(autocad_layer) = DELIM~DP~LIM~CAD;TEST @Value(autocad_layer) = DELIM~DP~LIM~DEC;TEST @Value(autocad_layer) = DELIM~OUVRA~PONT~PILE;TEST @Value(autocad_layer) = DELIM~OUVRA~PONT~TAB;TEST @Value(autocad_layer) = DELIM~OUVRA~00~-;TEST @Value(autocad_layer) = DELIM~SEUIL~-~PARK;TEST @Value(autocad_layer) = DELIM~SEUIL~-~CAVE;TEST @Value(autocad_layer) = DELIM~SEUIL~-~SOUP;TEST @Value(autocad_layer) = DELIM~SEUIL~-~VITRI;TEST @Value(autocad_layer) = DELIM~SEUIL~-~00;TEST @Value(autocad_layer) = DELIM~CLOT~CLOT~PAD_EP;TEST @Value(autocad_layer) = DELIM~CLOT~CLOT~PALI_EP;TEST @Value(autocad_layer) = DELIM~CLOT~CLOT~SOC_O_EP;TEST @Value(autocad_layer) = DELIM~CLOT~CLOT~SOC_N_EP;TEST @Value(autocad_layer) = DELIM~CLOT~CLOT~TREI_EP;TEST @Value(autocad_layer) = DELIM~CLOT~MUR~BAHU_N_EP;TEST @Value(autocad_layer) = DELIM~CLOT~MUR~BAHU_O_EP;TEST @Value(autocad_layer) = DELIM~CLOT~MUR~ENRO_EP;TEST @Value(autocad_layer) = DELIM~CLOT~MUR~MUR_EP;TEST @Value(autocad_layer) = DELIM~CLOT~MUR~PARA_EP;TEST @Value(autocad_layer) = DELIM~CLOT~MUR~SOUT_EP'L'BOOL_OP;OR;COMPOSITE_TEST;<Unused>;TEST @Value(autocad_layer) = DELIM~CLOT~PIL~CAR'PS_CAR'BOOL_OP;OR;COMPOSITE_TEST;<Unused>;TEST @Value(autocad_layer) = DELIM~CLOT~PIL~CIR'PS_CIR'BOOL_OP;OR;COMPOSITE_TEST;<Unused>;TEST @Value(autocad_layer) = DELIM~CLOT~PIL~OVA'PS_OVA'BOOL_OP;OR;COMPOSITE_TEST;<Unused>;TEST @Value(autocad_layer) = DELIM~CLOT~PIL~REC'PS_REC'BOOL_OP;OR;COMPOSITE_TEST;<Unused>;TEST @Value(autocad_layer) = DELIM~DP~AMOR~-'P'BOOL_OP;OR;COMPOSITE_TEST;<Unused>;TEST @Value(autocad_layer) = DELIM~DP~PAR~-'S'FME_NUM_CONDITIONS8___
    -> AttributeFilter_5

Bookmark: INFRA / Attribution FORME
Tester_12
    BOOL_OP = OR
    TEST_CLAUSE:
      TEST @Value(autocad_layer) = INFRA~FER~PAS~-
      TEST @Value(autocad_layer) = INFRA~FER~QUAI~RAIL
      TEST @Value(autocad_layer) = INFRA~FER~RAIL~-
      TEST @Value(autocad_layer) = INFRA~FER~TRAM~-
      TEST @Value(autocad_layer) = INFRA~MAR~QUAI~MAR
      TEST @Value(autocad_layer) = INFRA~ROU~ESCA~NEZ
      TEST @Value(autocad_layer) = INFRA~ROU~ESCA~PIED
      TEST @Value(autocad_layer) = INFRA~ROU~ESCA~VOL
      TEST @Value(autocad_layer) = INFRA~ROU~ESCA~PAL
      TEST @Value(autocad_layer) = INFRA~ROU~ACCOT~-
      TEST @Value(autocad_layer) = INFRA~ROU~BORD~BAS
      TEST @Value(autocad_layer) = INFRA~ROU~BORD~CHAU
      TEST @Value(autocad_layer) = INFRA~ROU~BORD~FRAN
      TEST @Value(autocad_layer) = INFRA~ROU~BORD~CIR
      TEST @Value(autocad_layer) = INFRA~ROU~BORD~HAUT
      TEST @Value(autocad_layer) = INFRA~ROU~DEPRES~-
      TEST @Value(autocad_layer) = INFRA~ROU~CANI~EAU
      TEST @Value(autocad_layer) = INFRA~ROU~SOL~-
      TEST @Value(autocad_layer) = INFRA~ROU~AXE~-
      TEST @Value(autocad_layer) = INFRA~ROU~BAND~-
      TEST @Value(autocad_layer) = INFRA~ROU~RAL~DOS
      TEST @Value(autocad_layer) = INFRA~ROU~RAL~FIXE
      TEST @Value(autocad_layer) = INFRA~ROU~RAL~PLAT
    TEST_MODE = TEST
    PASSED -> AttributeCreator_5
AttributeCreator_5
    ATTR_TABLE = SET_TO FORME = FME_CONDITIONAL:DEFAULT_VALUE'_FME_NO_OP_'BOOL_OP;OR;COMPOSITE_TEST;<Unused>;TEST @Value(autocad_layer) = INFRA~FER~PAS~-;TEST @Value(autocad_layer) = INFRA~FER~QUAI~RAIL;TEST @Value(autocad_layer) = INFRA~FER~RAIL~-;TEST @Value(autocad_layer) = INFRA~FER~TRAM~-;TEST @Value(autocad_layer) = INFRA~MAR~QUAI~MAR;TEST @Value(autocad_layer) = INFRA~ROU~ESCA~NEZ;TEST @Value(autocad_layer) = INFRA~ROU~ESCA~PIED;TEST @Value(autocad_layer) = INFRA~ROU~ACCOT~-;TEST @Value(autocad_layer) = INFRA~ROU~BORD~BAS;TEST @Value(autocad_layer) = INFRA~ROU~BORD~CHAU;TEST @Value(autocad_layer) = INFRA~ROU~BORD~FRAN;TEST @Value(autocad_layer) = INFRA~ROU~BORD~CIR;TEST @Value(autocad_layer) = INFRA~ROU~BORD~HAUT;TEST @Value(autocad_layer) = INFRA~ROU~DEPRES~-;TEST @Value(autocad_layer) = INFRA~ROU~CANI~EAU;TEST @Value(autocad_layer) = INFRA~ROU~SOL~-;TEST @Value(autocad_layer) = INFRA~ROU~AXE~-;TEST @Value(autocad_layer) = INFRA~ROU~BAND~-;TEST @Value(autocad_layer) = INFRA~ROU~RAL~DOS;TEST @Value(autocad_layer) = INFRA~ROU~RAL~PLAT'L'BOOL_OP;OR;COMPOSITE_TEST;<Unused>;TEST @Value(autocad_layer) = INFRA~ROU~ESCA~VOL;TEST @Value(autocad_layer) = INFRA~ROU~ESCA~PAL'S'BOOL_OP;OR;COMPOSITE_TEST;<Unused>;TEST @Value(autocad_layer) = INFRA~ROU~RAL~FIXE'PS_REC'FME_NUM_CONDITIONS4___
    -> AttributeFilter_5

Bookmark: NATURE / Attribution FORME
Tester_13
    BOOL_OP = OR
    TEST_CLAUSE:
      TEST @Value(autocad_layer) = NATURE~HYDRO~EAU~-
      TEST @Value(autocad_layer) = NATURE~TOPO~FOSSE~BAS
      TEST @Value(autocad_layer) = NATURE~TOPO~FOSSE~HAUT
      TEST @Value(autocad_layer) = NATURE~TOPO~TALUS~BAS
      TEST @Value(autocad_layer) = NATURE~TOPO~TALUS~HAUT
      TEST @Value(autocad_layer) = NATURE~VERT~ARB~CONI
      TEST @Value(autocad_layer) = NATURE~VERT~ARB~FEUIL
      TEST @Value(autocad_layer) = NATURE~VERT~ARB~00
      TEST @Value(autocad_layer) = NATURE~VERT~FAUNE~-
      TEST @Value(autocad_layer) = NATURE~VERT~BAC~CAR
      TEST @Value(autocad_layer) = NATURE~VERT~BAC~CIR
      TEST @Value(autocad_layer) = NATURE~VERT~BAC~REC
      TEST @Value(autocad_layer) = NATURE~VERT~BORD~VERT
      TEST @Value(autocad_layer) = NATURE~VERT~ESP~-
      TEST @Value(autocad_layer) = NATURE~VERT~HAIE~-
    TEST_MODE = TEST
    PASSED -> AttributeCreator_7
AttributeCreator_7
    ATTR_TABLE = SET_TO FORME = FME_CONDITIONAL:DEFAULT_VALUE'_FME_NO_OP_'BOOL_OP;OR;COMPOSITE_TEST;<Unused>;TEST @Value(autocad_layer) = NATURE~HYDRO~EAU~-;TEST @Value(autocad_layer) = NATURE~TOPO~FOSSE~BAS;TEST @Value(autocad_layer) = NATURE~TOPO~FOSSE~HAUT;TEST @Value(autocad_layer) = NATURE~TOPO~TALUS~BAS;TEST @Value(autocad_layer) = NATURE~TOPO~TALUS~HAUT;TEST @Value(autocad_layer) = NATURE~VERT~BORD~VERT;TEST @Value(autocad_layer) = NATURE~VERT~ESP~-;TEST @Value(autocad_layer) = NATURE~VERT~HAIE~-'L'BOOL_OP;OR;COMPOSITE_TEST;<Unused>;TEST @Value(autocad_layer) = NATURE~VERT~FAUNE~-;TEST @Value(autocad_layer) = NATURE~VERT~BAC~REC'PS_REC'BOOL_OP;OR;COMPOSITE_TEST;<Unused>;TEST @Value(autocad_layer) = NATURE~VERT~ARB~CONI;TEST @Value(autocad_layer) = NATURE~VERT~ARB~FEUIL;TEST @Value(autocad_layer) = NATURE~VERT~ARB~00;TEST @Value(autocad_layer) = NATURE~VERT~BAC~CIR'PS_CIR'BOOL_OP;OR;COMPOSITE_TEST;<Unused>;TEST @Value(autocad_layer) = NATURE~VERT~BAC~CAR'PS_CAR'FME_NUM_CONDITIONS5___
    -> AttributeFilter_5

Bookmark: RESEAU
AttributeFilter_4
    ATTR_NAME = SSTHEME
    ATTR_VALUES = <Empty>,<Missing>,<Null>,<Unfiltered>,00,AEP,ASSA,CHAU,ECL,VIDEO,ELEC,COM,INOLIA,GAZ,INCE,SLT,TRANS
    00 -> Tester_14
    AEP -> Tester_15
    ASSA -> Tester_16
    CHAU -> Tester_17
    ECL -> Tester_18
    VIDEO -> Tester_19
    ELEC -> Tester_20
    COM -> Tester_21
    INOLIA -> Tester_21
    GAZ -> Tester_22
    INCE -> Tester_24
    SLT -> Tester_24
    TRANS -> Tester_25

Bookmark: RESEAU~00 / Attribution forme
Tester_14
    BOOL_OP = OR
    TEST_CLAUSE:
      TEST @Value(autocad_layer) = RESEAU~00~ARM~ENCA
      TEST @Value(autocad_layer) = RESEAU~00~ARM~MAC
      TEST @Value(autocad_layer) = RESEAU~00~ARM~00
      TEST @Value(autocad_layer) = RESEAU~00~COF~ENCA
      TEST @Value(autocad_layer) = RESEAU~00~COF~MAC
      TEST @Value(autocad_layer) = RESEAU~00~COF~00
      TEST @Value(autocad_layer) = RESEAU~00~VAN~CAR
      TEST @Value(autocad_layer) = RESEAU~00~VAN~CIR
      TEST @Value(autocad_layer) = RESEAU~00~VAN~OVA
      TEST @Value(autocad_layer) = RESEAU~00~VAN~PEN
      TEST @Value(autocad_layer) = RESEAU~00~PLA~CAR
      TEST @Value(autocad_layer) = RESEAU~00~PLA~REC
      TEST @Value(autocad_layer) = RESEAU~00~POT~MAT
      TEST @Value(autocad_layer) = RESEAU~00~POT~POTEN
      TEST @Value(autocad_layer) = RESEAU~00~POT~PORT
      TEST @Value(autocad_layer) = RESEAU~00~POT~00
      TEST @Value(autocad_layer) = RESEAU~00~REG~CAR
      TEST @Value(autocad_layer) = RESEAU~00~REG~CIR
      TEST @Value(autocad_layer) = RESEAU~00~REG~OVA
      TEST @Value(autocad_layer) = RESEAU~00~REG~REC
      TEST @Value(autocad_layer) = RESEAU~00~REP~-
    TEST_MODE = TEST
    PASSED -> AttributeCreator_8
AttributeCreator_8
    ATTR_TABLE = SET_TO FORME = FME_CONDITIONAL:DEFAULT_VALUE'_FME_NO_OP_'BOOL_OP;OR;COMPOSITE_TEST;<Unused>;TEST @Value(autocad_layer) = RESEAU~00~ARM~MAC;TEST @Value(autocad_layer) = RESEAU~00~COF~MAC'L'BOOL_OP;OR;COMPOSITE_TEST;<Unused>;TEST @Value(autocad_layer) = RESEAU~00~ARM~ENCA;TEST @Value(autocad_layer) = RESEAU~00~ARM~00;TEST @Value(autocad_layer) = RESEAU~00~COF~ENCA;TEST @Value(autocad_layer) = RESEAU~00~COF~00;TEST @Value(autocad_layer) = RESEAU~00~PLA~REC;TEST @Value(autocad_layer) = RESEAU~00~REG~REC'PS_REC'BOOL_OP;OR;COMPOSITE_TEST;<Unused>;TEST @Value(autocad_layer) = RESEAU~00~REG~CIR'PS_CIR'BOOL_OP;OR;COMPOSITE_TEST;<Unused>;TEST @Value(autocad_layer) = RESEAU~00~PLA~CAR;TEST @Value(autocad_layer) = RESEAU~00~REG~CAR'PS_CAR'BOOL_OP;OR;COMPOSITE_TEST;<Unused>;TEST @Value(autocad_layer) = RESEAU~00~REG~OVA'PS_OVA'BOOL_OP;OR;COMPOSITE_TEST;<Unused>;TEST @Value(autocad_layer) = RESEAU~00~VAN~CAR;TEST @Value(autocad_layer) = RESEAU~00~VAN~CIR;TEST @Value(autocad_layer) = RESEAU~00~VAN~PEN;TEST @Value(autocad_layer) = RESEAU~00~POT~MAT;TEST @Value(autocad_layer) = RESEAU~00~POT~00;TEST @Value(autocad_layer) = RESEAU~00~REP~-;TEST @Value(autocad_layer) = RESEAU~00~VAN~OVA'P'BOOL_OP;OR;COMPOSITE_TEST;1 OR 2;TEST @Value(autocad_layer) = RESEAU~00~POT~POTEN;TEST @Value(autocad_layer) = RESEAU~00~POT~PORT'PL'FME_NUM_CONDITIONS8___
    -> AttributeFilter_5

Bookmark: RESEAU~AEP / Attribution forme
Tester_15
    BOOL_OP = OR
    TEST_CLAUSE:
      TEST @Value(autocad_layer) = RESEAU~AEP~BOU~ARRO
      TEST @Value(autocad_layer) = RESEAU~AEP~BOU~LAVA
      TEST @Value(autocad_layer) = RESEAU~AEP~VAN~CAR
      TEST @Value(autocad_layer) = RESEAU~AEP~VAN~CIR
      TEST @Value(autocad_layer) = RESEAU~AEP~VAN~OVA
      TEST @Value(autocad_layer) = RESEAU~AEP~VAN~PEN
      TEST @Value(autocad_layer) = RESEAU~AEP~VAN~REC
      TEST @Value(autocad_layer) = RESEAU~AEP~FONT~-
      TEST @Value(autocad_layer) = RESEAU~AEP~PUITS~-
      TEST @Value(autocad_layer) = RESEAU~AEP~REP~-
    TEST_MODE = TEST
    PASSED -> AttributeCreator_9
AttributeCreator_9
    ATTR_TABLE = SET_TO FORME = FME_CONDITIONAL:DEFAULT_VALUE'_FME_NO_OP_'BOOL_OP;OR;COMPOSITE_TEST;<Unused>;TEST @Value(autocad_layer) = RESEAU~AEP~PUITS~-'PS_CIR'BOOL_OP;OR;COMPOSITE_TEST;<Unused>;TEST @Value(autocad_layer) = RESEAU~AEP~BOU~ARRO;TEST @Value(autocad_layer) = RESEAU~AEP~BOU~LAVA;TEST @Value(autocad_layer) = RESEAU~AEP~VAN~CAR;TEST @Value(autocad_layer) = RESEAU~AEP~VAN~CIR;TEST @Value(autocad_layer) = RESEAU~AEP~VAN~OVA;TEST @Value(autocad_layer) = RESEAU~AEP~VAN~PEN;TEST @Value(autocad_layer) = RESEAU~AEP~VAN~REC;TEST @Value(autocad_layer) = RESEAU~AEP~FONT~-;TEST @Value(autocad_layer) = RESEAU~AEP~REP~-'P'FME_NUM_CONDITIONS3___
    -> AttributeFilter_5

Bookmark: RESEAU~ASSA / Attribution forme
Tester_16
    BOOL_OP = OR
    TEST_CLAUSE:
      TEST @Value(autocad_layer) = RESEAU~ASSA~AVA~GRILLE
      TEST @Value(autocad_layer) = RESEAU~ASSA~AVA~REGARD
      TEST @Value(autocad_layer) = RESEAU~ASSA~AVA~RE_GR
      TEST @Value(autocad_layer) = RESEAU~ASSA~AVA~D
      TEST @Value(autocad_layer) = RESEAU~ASSA~AVA~G
      TEST @Value(autocad_layer) = RESEAU~ASSA~AVA~00
      TEST @Value(autocad_layer) = RESEAU~ASSA~VAN~-
      TEST @Value(autocad_layer) = RESEAU~ASSA~GRIL~CAR
      TEST @Value(autocad_layer) = RESEAU~ASSA~GRIL~CIR
      TEST @Value(autocad_layer) = RESEAU~ASSA~GRIL~OVA
      TEST @Value(autocad_layer) = RESEAU~ASSA~GRIL~REC
      TEST @Value(autocad_layer) = RESEAU~ASSA~GRIL~COURB
      TEST @Value(autocad_layer) = RESEAU~ASSA~REG~CAR
      TEST @Value(autocad_layer) = RESEAU~ASSA~REG~CIR
    TEST_MODE = TEST
    PASSED -> AttributeCreator_10
AttributeCreator_10
    ATTR_TABLE = SET_TO FORME = FME_CONDITIONAL:DEFAULT_VALUE'_FME_NO_OP_'BOOL_OP;OR;COMPOSITE_TEST;<Unused>;TEST @Value(autocad_layer) = RESEAU~ASSA~GRIL~CIR;TEST @Value(autocad_layer) = RESEAU~ASSA~REG~CIR'PS_CIR'BOOL_OP;OR;COMPOSITE_TEST;<Unused>;TEST @Value(autocad_layer) = RESEAU~ASSA~VAN~-'P'BOOL_OP;OR;COMPOSITE_TEST;<Unused>;TEST @Value(autocad_layer) = RESEAU~ASSA~AVA~GRILLE;TEST @Value(autocad_layer) = RESEAU~ASSA~AVA~REGARD;TEST @Value(autocad_layer) = RESEAU~ASSA~AVA~RE_GR;TEST @Value(autocad_layer) = RESEAU~ASSA~AVA~D;TEST @Value(autocad_layer) = RESEAU~ASSA~AVA~G;TEST @Value(autocad_layer) = RESEAU~ASSA~AVA~00;TEST @Value(autocad_layer) = RESEAU~ASSA~GRIL~REC'PS_REC'BOOL_OP;OR;COMPOSITE_TEST;<Unused>;TEST @Value(autocad_layer) = RESEAU~ASSA~GRIL~CAR;TEST @Value(autocad_layer) = RESEAU~ASSA~REG~CAR'PS_CAR'BOOL_OP;OR;COMPOSITE_TEST;<Unused>;TEST @Value(autocad_layer) = RESEAU~ASSA~GRIL~OVA'PS_OVA'BOOL_OP;OR;COMPOSITE_TEST;<Unused>;TEST @Value(autocad_layer) = RESEAU~ASSA~GRIL~COURB'L'FME_NUM_CONDITIONS7___
    -> AttributeFilter_5

Bookmark: RESEAU~CHAU / Attribution forme
Tester_17
    BOOL_OP = OR
    TEST_CLAUSE:
      TEST @Value(autocad_layer) = RESEAU~CHAU~ARM~ENCA
      TEST @Value(autocad_layer) = RESEAU~CHAU~ARM~MAC
      TEST @Value(autocad_layer) = RESEAU~CHAU~ARM~00
      TEST @Value(autocad_layer) = RESEAU~CHAU~COF~ENCA
      TEST @Value(autocad_layer) = RESEAU~CHAU~COF~MAC
      TEST @Value(autocad_layer) = RESEAU~CHAU~COF~00
      TEST @Value(autocad_layer) = RESEAU~CHAU~VAN~CAR
      TEST @Value(autocad_layer) = RESEAU~CHAU~VAN~CIR
      TEST @Value(autocad_layer) = RESEAU~CHAU~VAN~OVA
      TEST @Value(autocad_layer) = RESEAU~CHAU~VAN~PEN
      TEST @Value(autocad_layer) = RESEAU~CHAU~PLA~CAR
      TEST @Value(autocad_layer) = RESEAU~CHAU~PLA~REC
      TEST @Value(autocad_layer) = RESEAU~CHAU~REG~CAR
      TEST @Value(autocad_layer) = RESEAU~CHAU~REG~CIR
      TEST @Value(autocad_layer) = RESEAU~CHAU~REG~OVA
      TEST @Value(autocad_layer) = RESEAU~CHAU~REG~REC
      TEST @Value(autocad_layer) = RESEAU~CHAU~REP~-
    TEST_MODE = TEST
    PASSED -> AttributeCreator_11
AttributeCreator_11
    ATTR_TABLE = SET_TO FORME = FME_CONDITIONAL:DEFAULT_VALUE'_FME_NO_OP_'BOOL_OP;OR;COMPOSITE_TEST;<Unused>;TEST @Value(autocad_layer) = RESEAU~CHAU~ARM~MAC;TEST @Value(autocad_layer) = RESEAU~CHAU~COF~MAC'L'BOOL_OP;OR;COMPOSITE_TEST;<Unused>;TEST @Value(autocad_layer) = RESEAU~CHAU~ARM~ENCA;TEST @Value(autocad_layer) = RESEAU~CHAU~ARM~00;TEST @Value(autocad_layer) = RESEAU~CHAU~COF~ENCA;TEST @Value(autocad_layer) = RESEAU~CHAU~COF~00;TEST @Value(autocad_layer) = RESEAU~CHAU~PLA~REC;TEST @Value(autocad_layer) = RESEAU~CHAU~REG~REC'PS_REC'BOOL_OP;OR;COMPOSITE_TEST;<Unused>;TEST @Value(autocad_layer) = RESEAU~CHAU~REG~CIR'PS_CIR'BOOL_OP;OR;COMPOSITE_TEST;<Unused>;TEST @Value(autocad_layer) = RESEAU~CHAU~PLA~CAR;TEST @Value(autocad_layer) = RESEAU~CHAU~REG~CAR'PS_CAR'BOOL_OP;OR;COMPOSITE_TEST;<Unused>;TEST @Value(autocad_layer) = RESEAU~CHAU~REG~OVA'PS_OVA'BOOL_OP;OR;COMPOSITE_TEST;<Unused>;TEST @Value(autocad_layer) = RESEAU~CHAU~VAN~CAR;TEST @Value(autocad_layer) = RESEAU~CHAU~VAN~CIR;TEST @Value(autocad_layer) = RESEAU~CHAU~VAN~OVA;TEST @Value(autocad_layer) = RESEAU~CHAU~VAN~PEN;TEST @Value(autocad_layer) = RESEAU~CHAU~REP~-'P'FME_NUM_CONDITIONS7___
    -> AttributeFilter_5

Bookmark: RESEAU~ECL / Attribution forme
Tester_18
    BOOL_OP = OR
    TEST_CLAUSE:
      TEST @Value(autocad_layer) = RESEAU~ECL~ARM~ENCA
      TEST @Value(autocad_layer) = RESEAU~ECL~ARM~MAC
      TEST @Value(autocad_layer) = RESEAU~ECL~ARM~00
      TEST @Value(autocad_layer) = RESEAU~ECL~COF~ENCA
      TEST @Value(autocad_layer) = RESEAU~ECL~COF~MAC
      TEST @Value(autocad_layer) = RESEAU~ECL~COF~00
      TEST @Value(autocad_layer) = RESEAU~ECL~LAMP~S
      TEST @Value(autocad_layer) = RESEAU~ECL~LAMP~D
      TEST @Value(autocad_layer) = RESEAU~ECL~LAMP~T
      TEST @Value(autocad_layer) = RESEAU~ECL~LAMP~Q
      TEST @Value(autocad_layer) = RESEAU~ECL~PLA~CAR
      TEST @Value(autocad_layer) = RESEAU~ECL~PLA~REC
      TEST @Value(autocad_layer) = RESEAU~ECL~SUP~-
      TEST @Value(autocad_layer) = RESEAU~ECL~REP~-
      TEST @Value(autocad_layer) = RESEAU~ECL~LUMI~CAR
      TEST @Value(autocad_layer) = RESEAU~ECL~LUMI~REC
      TEST @Value(autocad_layer) = RESEAU~ECL~LUMI~CONS
      TEST @Value(autocad_layer) = RESEAU~ECL~LUMI~CIR
      TEST @Value(autocad_layer) = RESEAU~ECL~LUMI~OVA
      TEST @Value(autocad_layer) = RESEAU~ECL~LUMI~SUS
    TEST_MODE = TEST
    PASSED -> AttributeCreator_12
AttributeCreator_12
    ATTR_TABLE = SET_TO FORME = FME_CONDITIONAL:DEFAULT_VALUE'_FME_NO_OP_'BOOL_OP;OR;COMPOSITE_TEST;<Unused>;TEST @Value(autocad_layer) = RESEAU~ECL~ARM~MAC;TEST @Value(autocad_layer) = RESEAU~ECL~COF~MAC'L'BOOL_OP;OR;COMPOSITE_TEST;<Unused>;TEST @Value(autocad_layer) = RESEAU~ECL~ARM~ENCA;TEST @Value(autocad_layer) = RESEAU~ECL~ARM~00;TEST @Value(autocad_layer) = RESEAU~ECL~COF~ENCA;TEST @Value(autocad_layer) = RESEAU~ECL~COF~00;TEST @Value(autocad_layer) = RESEAU~ECL~PLA~REC;TEST @Value(autocad_layer) = RESEAU~ECL~LUMI~REC'PS_REC'BOOL_OP;OR;COMPOSITE_TEST;<Unused>;TEST @Value(autocad_layer) = RESEAU~ECL~PLA~CAR;TEST @Value(autocad_layer) = RESEAU~ECL~LUMI~CAR'PS_CAR'BOOL_OP;OR;COMPOSITE_TEST;<Unused>;TEST @Value(autocad_layer) = RESEAU~ECL~REP~-;TEST @Value(autocad_layer) = RESEAU~ECL~LAMP~S;TEST @Value(autocad_layer) = RESEAU~ECL~LAMP~D;TEST @Value(autocad_layer) = RESEAU~ECL~LAMP~T;TEST @Value(autocad_layer) = RESEAU~ECL~LAMP~Q;TEST @Value(autocad_layer) = RESEAU~ECL~SUP~-;TEST @Value(autocad_layer) = RESEAU~ECL~LUMI~CONS;TEST @Value(autocad_layer) = RESEAU~ECL~LUMI~SUS'P'BOOL_OP;OR;COMPOSITE_TEST;<Unused>;TEST @Value(autocad_layer) = RESEAU~ECL~LUMI~CIR'PS_CIR'BOOL_OP;OR;COMPOSITE_TEST;<Unused>;TEST @Value(autocad_layer) = RESEAU~ECL~LUMI~OVA'PS_OVA'FME_NUM_CONDITIONS7___
    -> AttributeFilter_5

Bookmark: RESEAU~VIDEO / Attribution forme
Tester_19
    BOOL_OP = OR
    TEST_CLAUSE:
      TEST @Value(autocad_layer) = RESEAU~VIDEO~BORN~ACCES
      TEST @Value(autocad_layer) = RESEAU~VIDEO~BORN~RETRA
      TEST @Value(autocad_layer) = RESEAU~VIDEO~BOUCLE~RETRA
      TEST @Value(autocad_layer) = RESEAU~VIDEO~CAM~CONS
      TEST @Value(autocad_layer) = RESEAU~VIDEO~CAM~POT
      TEST @Value(autocad_layer) = RESEAU~VIDEO~POT_FEU~ACCES
    TEST_MODE = TEST
    PASSED -> AttributeCreator_13
AttributeCreator_13
    ATTR_TABLE = SET_TO FORME = FME_CONDITIONAL:DEFAULT_VALUE'_FME_NO_OP_'BOOL_OP;OR;COMPOSITE_TEST;<Unused>;TEST @Value(autocad_layer) = RESEAU~VIDEO~BOUCLE~RETRA'L'BOOL_OP;OR;COMPOSITE_TEST;<Unused>;TEST @Value(autocad_layer) = RESEAU~VIDEO~BORN~ACCES'PS_REC'BOOL_OP;OR;COMPOSITE_TEST;<Unused>;TEST @Value(autocad_layer) = RESEAU~VIDEO~CAM~CONS;TEST @Value(autocad_layer) = RESEAU~VIDEO~CAM~POT;TEST @Value(autocad_layer) = RESEAU~VIDEO~POT_FEU~ACCES'P'BOOL_OP;OR;COMPOSITE_TEST;<Unused>;TEST @Value(autocad_layer) = RESEAU~VIDEO~BORN~RETRA'PS_CIR'FME_NUM_CONDITIONS5___
    -> AttributeFilter_5

Bookmark: RESEAU~ELEC / Attribution forme
Tester_20
    BOOL_OP = OR
    TEST_CLAUSE:
      TEST @Value(autocad_layer) = RESEAU~ELEC~ARM~ENCA
      TEST @Value(autocad_layer) = RESEAU~ELEC~ARM~MAC
      TEST @Value(autocad_layer) = RESEAU~ELEC~ARM~00
      TEST @Value(autocad_layer) = RESEAU~ELEC~COF~ENCA
      TEST @Value(autocad_layer) = RESEAU~ELEC~COF~MAC
      TEST @Value(autocad_layer) = RESEAU~ELEC~COF~00
      TEST @Value(autocad_layer) = RESEAU~ELEC~SUP~BT_CAR
      TEST @Value(autocad_layer) = RESEAU~ELEC~SUP~BT_CIR
      TEST @Value(autocad_layer) = RESEAU~ELEC~SUP~PYL
      TEST @Value(autocad_layer) = RESEAU~ELEC~SUP~HT
      TEST @Value(autocad_layer) = RESEAU~ELEC~SUP~MT
      TEST @Value(autocad_layer) = RESEAU~ELEC~SUP~THT
      TEST @Value(autocad_layer) = RESEAU~ELEC~PLA~CAR
      TEST @Value(autocad_layer) = RESEAU~ELEC~PLA~REC
      TEST @Value(autocad_layer) = RESEAU~ELEC~TRANS~-
      TEST @Value(autocad_layer) = RESEAU~ELEC~PRISE~-
      TEST @Value(autocad_layer) = RESEAU~ELEC~REP~-
    TEST_MODE = TEST
    PASSED -> AttributeCreator_14
AttributeCreator_14
    ATTR_TABLE = SET_TO FORME = FME_CONDITIONAL:DEFAULT_VALUE'_FME_NO_OP_'BOOL_OP;OR;COMPOSITE_TEST;<Unused>;TEST @Value(autocad_layer) = RESEAU~ELEC~ARM~MAC;TEST @Value(autocad_layer) = RESEAU~ELEC~COF~MAC;TEST @Value(autocad_layer) = RESEAU~ELEC~TRANS~-'L'BOOL_OP;OR;COMPOSITE_TEST;<Unused>;TEST @Value(autocad_layer) = RESEAU~ELEC~ARM~ENCA;TEST @Value(autocad_layer) = RESEAU~ELEC~ARM~00;TEST @Value(autocad_layer) = RESEAU~ELEC~COF~ENCA;TEST @Value(autocad_layer) = RESEAU~ELEC~COF~00;TEST @Value(autocad_layer) = RESEAU~ELEC~PLA~REC;TEST @Value(autocad_layer) = RESEAU~ELEC~SUP~PYL'PS_REC'BOOL_OP;OR;COMPOSITE_TEST;<Unused>;TEST @Value(autocad_layer) = RESEAU~ELEC~PLA~CAR'PS_CAR'BOOL_OP;OR;COMPOSITE_TEST;<Unused>;TEST @Value(autocad_layer) = RESEAU~ELEC~SUP~BT_CAR;TEST @Value(autocad_layer) = RESEAU~ELEC~SUP~BT_CIR;TEST @Value(autocad_layer) = RESEAU~ELEC~SUP~HT;TEST @Value(autocad_layer) = RESEAU~ELEC~SUP~MT;TEST @Value(autocad_layer) = RESEAU~ELEC~SUP~THT;TEST @Value(autocad_layer) = RESEAU~ELEC~PRISE~-;TEST @Value(autocad_layer) = RESEAU~ELEC~REP~-'P'FME_NUM_CONDITIONS5___
    -> AttributeFilter_5

Bookmark: RESEAU~COM/INOLIA / Attribution forme
Tester_21
    BOOL_OP = OR
    TEST_CLAUSE:
      TEST @Value(autocad_layer) = RESEAU~COM~COF~ENCA
      TEST @Value(autocad_layer) = RESEAU~COM~COF~MAC
      TEST @Value(autocad_layer) = RESEAU~COM~COF~00
      TEST @Value(autocad_layer) = RESEAU~COM~PLA~CAR
      TEST @Value(autocad_layer) = RESEAU~COM~PLA~REC
      TEST @Value(autocad_layer) = RESEAU~COM~SUP~REN_O
      TEST @Value(autocad_layer) = RESEAU~COM~SUP~REN_N
      TEST @Value(autocad_layer) = RESEAU~COM~REP~-
      TEST @Value(autocad_layer) = RESEAU~INOLIA~PLA~CAR
      TEST @Value(autocad_layer) = RESEAU~INOLIA~PLA~REC
      TEST @Value(autocad_layer) = RESEAU~INOLIA~REP~-
    TEST_MODE = TEST
    PASSED -> AttributeCreator_15
AttributeCreator_15
    ATTR_TABLE = SET_TO FORME = FME_CONDITIONAL:DEFAULT_VALUE'_FME_NO_OP_'BOOL_OP;OR;COMPOSITE_TEST;<Unused>;TEST @Value(autocad_layer) = RESEAU~COM~COF~MAC'L'BOOL_OP;OR;COMPOSITE_TEST;<Unused>;TEST @Value(autocad_layer) = RESEAU~COM~COF~ENCA;TEST @Value(autocad_layer) = RESEAU~COM~COF~00;TEST @Value(autocad_layer) = RESEAU~COM~PLA~REC;TEST @Value(autocad_layer) = RESEAU~INOLIA~PLA~REC'PS_REC'BOOL_OP;OR;COMPOSITE_TEST;<Unused>;TEST @Value(autocad_layer) = RESEAU~COM~PLA~CAR;TEST @Value(autocad_layer) = RESEAU~INOLIA~PLA~CAR'PS_CAR'BOOL_OP;OR;COMPOSITE_TEST;<Unused>;TEST @Value(autocad_layer) = RESEAU~COM~SUP~REN_N;TEST @Value(autocad_layer) = RESEAU~COM~REP~-;TEST @Value(autocad_layer) = RESEAU~INOLIA~REP~-'P'BOOL_OP;OR;COMPOSITE_TEST;<Unused>;TEST @Value(autocad_layer) = RESEAU~COM~SUP~REN_O'PL'FME_NUM_CONDITIONS6___
    -> AttributeFilter_5

Bookmark: RESEAU~GAZ / Attribution forme
Tester_22
    BOOL_OP = OR
    TEST_CLAUSE:
      TEST @Value(autocad_layer) = RESEAU~GAZ~ARM~ENCA
      TEST @Value(autocad_layer) = RESEAU~GAZ~ARM~MAC
      TEST @Value(autocad_layer) = RESEAU~GAZ~ARM~00
      TEST @Value(autocad_layer) = RESEAU~GAZ~COF~ENCA
      TEST @Value(autocad_layer) = RESEAU~GAZ~COF~MAC
      TEST @Value(autocad_layer) = RESEAU~GAZ~COF~00
      TEST @Value(autocad_layer) = RESEAU~GAZ~VAN~CAR
      TEST @Value(autocad_layer) = RESEAU~GAZ~VAN~CIR
      TEST @Value(autocad_layer) = RESEAU~GAZ~VAN~OVA
      TEST @Value(autocad_layer) = RESEAU~GAZ~VAN~PEN
      TEST @Value(autocad_layer) = RESEAU~GAZ~PLA~CAR
      TEST @Value(autocad_layer) = RESEAU~GAZ~PLA~REC
      TEST @Value(autocad_layer) = RESEAU~GAZ~REG~CAR
      TEST @Value(autocad_layer) = RESEAU~GAZ~REG~CIR
      TEST @Value(autocad_layer) = RESEAU~GAZ~REG~OVA
      TEST @Value(autocad_layer) = RESEAU~GAZ~REG~REC
      TEST @Value(autocad_layer) = RESEAU~GAZ~REP~-
    TEST_MODE = TEST
    PASSED -> AttributeCreator_16
AttributeCreator_16
    ATTR_TABLE = SET_TO FORME = FME_CONDITIONAL:DEFAULT_VALUE'_FME_NO_OP_'BOOL_OP;OR;COMPOSITE_TEST;<Unused>;TEST @Value(autocad_layer) = RESEAU~GAZ~ARM~MAC;TEST @Value(autocad_layer) = RESEAU~GAZ~COF~MAC'L'BOOL_OP;OR;COMPOSITE_TEST;<Unused>;TEST @Value(autocad_layer) = RESEAU~GAZ~ARM~ENCA;TEST @Value(autocad_layer) = RESEAU~GAZ~ARM~00;TEST @Value(autocad_layer) = RESEAU~GAZ~COF~ENCA;TEST @Value(autocad_layer) = RESEAU~GAZ~COF~00;TEST @Value(autocad_layer) = RESEAU~GAZ~PLA~REC;TEST @Value(autocad_layer) = RESEAU~GAZ~REG~REC'PS_REC'BOOL_OP;OR;COMPOSITE_TEST;<Unused>;TEST @Value(autocad_layer) = RESEAU~GAZ~REG~CIR'PS_CIR'BOOL_OP;OR;COMPOSITE_TEST;<Unused>;TEST @Value(autocad_layer) = RESEAU~GAZ~PLA~CAR;TEST @Value(autocad_layer) = RESEAU~GAZ~REG~CAR'PS_CAR'BOOL_OP;OR;COMPOSITE_TEST;<Unused>;TEST @Value(autocad_layer) = RESEAU~GAZ~REG~OVA'PS_OVA'BOOL_OP;OR;COMPOSITE_TEST;<Unused>;TEST @Value(autocad_layer) = RESEAU~GAZ~VAN~CAR;TEST @Value(autocad_layer) = RESEAU~GAZ~VAN~CIR;TEST @Value(autocad_layer) = RESEAU~GAZ~VAN~OVA;TEST @Value(autocad_layer) = RESEAU~GAZ~VAN~PEN;TEST @Value(autocad_layer) = RESEAU~GAZ~REP~-'P'FME_NUM_CONDITIONS7___
    -> AttributeFilter_5

Bookmark: RESEAU~INCE/STL / Attribution forme
Tester_24
    BOOL_OP = OR
    TEST_CLAUSE:
      TEST @Value(autocad_layer) = RESEAU~INCE~BORN~-
      TEST @Value(autocad_layer) = RESEAU~INCE~MAT~-
      TEST @Value(autocad_layer) = RESEAU~INCE~BOU~-
      TEST @Value(autocad_layer) = RESEAU~SLT~PLA~CAR
      TEST @Value(autocad_layer) = RESEAU~SLT~PLA~REC
      TEST @Value(autocad_layer) = RESEAU~SLT~FLASH~-
      TEST @Value(autocad_layer) = RESEAU~SLT~BOUCLE~FEU
      TEST @Value(autocad_layer) = RESEAU~SLT~LUMI~SOL
      TEST @Value(autocad_layer) = RESEAU~SLT~REF~-
      TEST @Value(autocad_layer) = RESEAU~SLT~POT_FEU~PIET
      TEST @Value(autocad_layer) = RESEAU~SLT~POT_FEU~UNI
      TEST @Value(autocad_layer) = RESEAU~SLT~POT_TRI~MAT
      TEST @Value(autocad_layer) = RESEAU~SLT~POT_TRI~POTEN
      TEST @Value(autocad_layer) = RESEAU~SLT~POT_TRI~PORT
      TEST @Value(autocad_layer) = RESEAU~SLT~POT_TRI~00
      TEST @Value(autocad_layer) = RESEAU~SLT~POT~VARIA
      TEST @Value(autocad_layer) = RESEAU~SLT~REP~-
    TEST_MODE = TEST
    PASSED -> AttributeCreator_17
AttributeCreator_17
    ATTR_TABLE = SET_TO FORME = FME_CONDITIONAL:DEFAULT_VALUE'_FME_NO_OP_'BOOL_OP;OR;COMPOSITE_TEST;<Unused>;TEST @Value(autocad_layer) = RESEAU~SLT~BOUCLE~FEU'L'BOOL_OP;OR;COMPOSITE_TEST;1 OR 2 OR 3 OR 4;TEST @Value(autocad_layer) = RESEAU~INCE~BOU~-;TEST @Value(autocad_layer) = RESEAU~SLT~PLA~REC;TEST @Value(autocad_layer) = RESEAU~SLT~REF~-;TEST @Value(autocad_layer) = RESEAU~SLT~FLASH~-'PS_REC'BOOL_OP;OR;COMPOSITE_TEST;<Unused>;TEST @Value(autocad_layer) = RESEAU~SLT~POT_TRI~POTEN;TEST @Value(autocad_layer) = RESEAU~SLT~POT_TRI~PORT'PL'BOOL_OP;OR;COMPOSITE_TEST;<Unused>;TEST @Value(autocad_layer) = RESEAU~SLT~PLA~CAR'PS_CAR'BOOL_OP;OR;COMPOSITE_TEST;1 OR 2 OR 3 OR 4 OR 5 OR 6 OR 7 OR 8 OR 9;TEST @Value(autocad_layer) = RESEAU~INCE~BORN~-;TEST @Value(autocad_layer) = RESEAU~INCE~MAT~-;TEST @Value(autocad_layer) = RESEAU~SLT~LUMI~SOL;TEST @Value(autocad_layer) = RESEAU~SLT~POT_FEU~PIET;TEST @Value(autocad_layer) = RESEAU~SLT~POT_FEU~UNI;TEST @Value(autocad_layer) = RESEAU~SLT~POT_TRI~MAT;TEST @Value(autocad_layer) = RESEAU~SLT~POT_TRI~00;TEST @Value(autocad_layer) = RESEAU~SLT~POT~VARIA;TEST @Value(autocad_layer) = RESEAU~SLT~REP~-'P'FME_NUM_CONDITIONS6___
    -> AttributeFilter_5

Bookmark: RESEAU~TRANS / Attribution forme
Tester_25
    BOOL_OP = OR
    TEST_CLAUSE:
      TEST @Value(autocad_layer) = RESEAU~TRANS~AUBETTE~BUS
      TEST @Value(autocad_layer) = RESEAU~TRANS~AUBETTE~TRAM
      TEST @Value(autocad_layer) = RESEAU~TRANS~BORN~TITRE
      TEST @Value(autocad_layer) = RESEAU~TRANS~CATE~S
      TEST @Value(autocad_layer) = RESEAU~TRANS~CATE~D
      TEST @Value(autocad_layer) = RESEAU~TRANS~APS~-
      TEST @Value(autocad_layer) = RESEAU~TRANS~POT_FEU~TRAM
      TEST @Value(autocad_layer) = RESEAU~TRANS~POT~BUS
      TEST @Value(autocad_layer) = RESEAU~TRANS~CAM~POT
      TEST @Value(autocad_layer) = RESEAU~TRANS~TITRE~-
      TEST @Value(autocad_layer) = RESEAU~TRANS~LIB~-
      TEST @Value(autocad_layer) = RESEAU~TRANS~REP~-
    TEST_MODE = TEST
    PASSED -> AttributeCreator_18
AttributeCreator_18
    ATTR_TABLE = SET_TO FORME = FME_CONDITIONAL:DEFAULT_VALUE'_FME_NO_OP_'BOOL_OP;OR;COMPOSITE_TEST;<Unused>;TEST @Value(autocad_layer) = RESEAU~TRANS~APS~-'L'BOOL_OP;OR;COMPOSITE_TEST;<Unused>;TEST @Value(autocad_layer) = RESEAU~TRANS~AUBETTE~BUS;TEST @Value(autocad_layer) = RESEAU~TRANS~AUBETTE~TRAM;TEST @Value(autocad_layer) = RESEAU~TRANS~BORN~TITRE;TEST @Value(autocad_layer) = RESEAU~TRANS~TITRE~-'PS_REC'BOOL_OP;OR;COMPOSITE_TEST;<Unused>;TEST @Value(autocad_layer) = RESEAU~TRANS~CATE~S;TEST @Value(autocad_layer) = RESEAU~TRANS~CATE~D;TEST @Value(autocad_layer) = RESEAU~TRANS~CAM~POT;TEST @Value(autocad_layer) = RESEAU~TRANS~POT_FEU~TRAM;TEST @Value(autocad_layer) = RESEAU~TRANS~POT~BUS;TEST @Value(autocad_layer) = RESEAU~TRANS~LIB~-;TEST @Value(autocad_layer) = RESEAU~TRANS~REP~-'P'FME_NUM_CONDITIONS4___
    -> AttributeFilter_5

Bookmark: Intégration des erreurs traitées
Note: ERROR pré-existantes
Junction_130
    -> AttributeExposer
Note: autocad_color
AttributeExposer
    ATTR_LIST = autocad_color
    -> Tester_95
Note: Error verte: traitée
Tester_95
    BOOL_OP = OR
    COMPOSITE_TEST = 1
    TEST_CLAUSE = TEST @Value(autocad_color) = 3
    TEST_MODE = TEST
    PASSED -> AttributeCreator_109
Note: ERROR_traitee=Oui
AttributeCreator_109
    ATTR_TABLE = SET_TO ERROR_traitee = Oui
    -> AttributeManager_8
Note: SSTHEME -> ERREUR
AttributeManager_8
    ATTR_TABLE = RENAME_SET_VALUE SSTHEME > ERREUR
    -> CenterPointExtractor_4
    -> AttributeKeeper_2

Bookmark: MOB / Attribution FORME
Tester_28
    BOOL_OP = OR
    COMPOSITE_TEST = 1 OR 2 OR 3 OR 4 OR 5 OR 6 OR 7 OR 8 OR 9 OR 10 OR 11 OR 12 OR 13 OR 14 OR 15 OR 16 OR 17 OR 18 OR 19 OR 20 OR 21 OR 22 OR 23 OR 24 OR 25 OR 26 OR 27 OR 28 OR 29 OR 30 OR 31
    TEST_CLAUSE:
      TEST @Value(autocad_layer) = MOB~DECH~CONT~-
      TEST @Value(autocad_layer) = MOB~DECH~CORB~-
      TEST @Value(autocad_layer) = MOB~DECH~POUB~-
      TEST @Value(autocad_layer) = MOB~PROT~ARC~PROT
      TEST @Value(autocad_layer) = MOB~PROT~BALI~-
      TEST @Value(autocad_layer) = MOB~PROT~BLOC~CAR
      TEST @Value(autocad_layer) = MOB~PROT~BLOC~REC
      TEST @Value(autocad_layer) = MOB~PROT~POT~BAR_O
      TEST @Value(autocad_layer) = MOB~PROT~POT~BAR_N
      TEST @Value(autocad_layer) = MOB~PROT~GLIS~BAS
      TEST @Value(autocad_layer) = MOB~PROT~GLIS~HAUT
      TEST @Value(autocad_layer) = MOB~PROT~GLIS~AXE
      TEST @Value(autocad_layer) = MOB~SANI~SANI~-
      TEST @Value(autocad_layer) = MOB~SANI~TOILE~-
      TEST @Value(autocad_layer) = MOB~PUB~SUP~CIR
      TEST @Value(autocad_layer) = MOB~PUB~SUP~MAT
      TEST @Value(autocad_layer) = MOB~PUB~SUP~PORT
      TEST @Value(autocad_layer) = MOB~PUB~SUP~REC
      TEST @Value(autocad_layer) = MOB~PUB~SUP~TRI
      TEST @Value(autocad_layer) = MOB~PUB~SUP~POTEN
      TEST @Value(autocad_layer) = MOB~URB~ARC~STAT
      TEST @Value(autocad_layer) = MOB~URB~BANC~-
      TEST @Value(autocad_layer) = MOB~URB~BAL~-
      TEST @Value(autocad_layer) = MOB~URB~BORN~OGE
      TEST @Value(autocad_layer) = MOB~URB~DRAP~-
      TEST @Value(autocad_layer) = MOB~URB~HORO~-
      TEST @Value(autocad_layer) = MOB~URB~STATU~-
      TEST @Value(autocad_layer) = MOB~URB~SUP~-
      TEST @Value(autocad_layer) = MOB~PROT~BORN~CAR
      TEST @Value(autocad_layer) = MOB~PROT~BORN~REC
      TEST @Value(autocad_layer) = MOB~PROT~BORN~CIR
    TEST_MODE = TEST
    PASSED -> AttributeCreator_21
AttributeCreator_21
    ATTR_TABLE = SET_TO FORME = FME_CONDITIONAL:DEFAULT_VALUE'_FME_NO_OP_'BOOL_OP;OR;COMPOSITE_TEST;<Unused>;TEST @Value(autocad_layer) = MOB~PROT~BALI~-;TEST @Value(autocad_layer) = MOB~PROT~POT~BAR_N;TEST @Value(autocad_layer) = MOB~PUB~SUP~MAT;TEST @Value(autocad_layer) = MOB~URB~BORN~OGE;TEST @Value(autocad_layer) = MOB~URB~DRAP~-'P'BOOL_OP;OR;COMPOSITE_TEST;1 OR 2 OR 3 OR 4 OR 5 OR 6 OR 7 OR 8;TEST @Value(autocad_layer) = MOB~PROT~ARC~PROT;TEST @Value(autocad_layer) = MOB~PROT~POT~BAR_O;TEST @Value(autocad_layer) = MOB~PROT~GLIS~BAS;TEST @Value(autocad_layer) = MOB~PROT~GLIS~HAUT;TEST @Value(autocad_layer) = MOB~PROT~GLIS~AXE;TEST @Value(autocad_layer) = MOB~SANI~SANI~-;TEST @Value(autocad_layer) = MOB~URB~ARC~STAT;TEST @Value(autocad_layer) = MOB~URB~STATU~-'L'BOOL_OP;OR;COMPOSITE_TEST;1 OR 2;TEST @Value(autocad_layer) = MOB~PROT~BLOC~CAR;TEST @Value(autocad_layer) = MOB~PROT~BORN~CAR'PS_CAR'BOOL_OP;OR;COMPOSITE_TEST;1 OR 2 OR 3 OR 4 OR 5 OR 6 OR 7 OR 8 OR 9 OR 10;TEST @Value(autocad_layer) = MOB~DECH~CONT~-;TEST @Value(autocad_layer) = MOB~DECH~POUB~-;TEST @Value(autocad_layer) = MOB~PROT~BLOC~REC;TEST @Value(autocad_layer) = MOB~SANI~TOILE~-;TEST @Value(autocad_layer) = MOB~PUB~SUP~REC;TEST @Value(autocad_layer) = MOB~URB~BANC~-;TEST @Value(autocad_layer) = MOB~URB~BAL~-;TEST @Value(autocad_layer) = MOB~URB~HORO~-;TEST @Value(autocad_layer) = MOB~URB~SUP~-;TEST @Value(autocad_layer) = MOB~PROT~BORN~REC'PS_REC'BOOL_OP;OR;COMPOSITE_TEST;1 OR 2 OR 3 OR 4;TEST @Value(autocad_layer) = MOB~DECH~CORB~-;TEST @Value(autocad_layer) = MOB~PUB~SUP~CIR;TEST @Value(autocad_layer) = MOB~PUB~SUP~TRI;TEST @Value(autocad_layer) = MOB~PROT~BORN~CIR'PS_CIR'BOOL_OP;OR;COMPOSITE_TEST;1 OR 2;TEST @Value(autocad_layer) = MOB~PUB~SUP~PORT;TEST @Value(autocad_layer) = MOB~PUB~SUP~POTEN'PL'FME_NUM_CONDITIONS7___
    -> AttributeFilter_5

Bookmark: SIGN / Attribution FORME
Tester_27
    BOOL_OP = OR
    TEST_CLAUSE:
      TEST @Value(autocad_layer) = SIGN~V~BORN~KILO
      TEST @Value(autocad_layer) = SIGN~V~POT_FER~MAT
      TEST @Value(autocad_layer) = SIGN~V~POT_FER~POTEN
      TEST @Value(autocad_layer) = SIGN~V~POT_FER~PORT
      TEST @Value(autocad_layer) = SIGN~V~POT_FER~00
      TEST @Value(autocad_layer) = SIGN~V~POT_JAL~ITI
      TEST @Value(autocad_layer) = SIGN~V~POT_JAL~ITI_PORT
      TEST @Value(autocad_layer) = SIGN~V~POT_JAL~LOC
      TEST @Value(autocad_layer) = SIGN~V~POT_JAL~LOC_PORT
      TEST @Value(autocad_layer) = SIGN~V~POT_JAL~PUB
      TEST @Value(autocad_layer) = SIGN~V~POT_JAL~PUB_PORT
      TEST @Value(autocad_layer) = SIGN~V~POT_ROU~MAT
      TEST @Value(autocad_layer) = SIGN~V~POT_ROU~POTEN
      TEST @Value(autocad_layer) = SIGN~V~POT_ROU~PORT
      TEST @Value(autocad_layer) = SIGN~V~POT_ROU~00
      TEST @Value(autocad_layer) = SIGN~V~PORT~-
      TEST @Value(autocad_layer) = SIGN~V~POT~RUE
      TEST @Value(autocad_layer) = SIGN~V~POT~BUS
      TEST @Value(autocad_layer) = SIGN~V~POT~VILLE
    TEST_MODE = TEST
    PASSED -> AttributeCreator_20
AttributeCreator_20
    ATTR_TABLE = SET_TO FORME = FME_CONDITIONAL:DEFAULT_VALUE'_FME_NO_OP_'BOOL_OP;OR;COMPOSITE_TEST;1 OR 2 OR 3 OR 4 OR 5 OR 6 OR 7 OR 8;TEST @Value(autocad_layer) = SIGN~V~POT_FER~POTEN;TEST @Value(autocad_layer) = SIGN~V~POT_FER~PORT;TEST @Value(autocad_layer) = SIGN~V~POT_ROU~POTEN;TEST @Value(autocad_layer) = SIGN~V~POT_ROU~PORT;TEST @Value(autocad_layer) = SIGN~V~POT_JAL~ITI_PORT;TEST @Value(autocad_layer) = SIGN~V~POT_JAL~LOC_PORT;TEST @Value(autocad_layer) = SIGN~V~POT_JAL~PUB_PORT;TEST @Value(autocad_layer) = SIGN~V~PORT~-'PL'BOOL_OP;OR;COMPOSITE_TEST;<Unused>;TEST @Value(autocad_layer) = SIGN~V~BORN~KILO;TEST @Value(autocad_layer) = SIGN~V~POT_FER~MAT;TEST @Value(autocad_layer) = SIGN~V~POT_FER~00;TEST @Value(autocad_layer) = SIGN~V~POT_JAL~ITI;TEST @Value(autocad_layer) = SIGN~V~POT_JAL~LOC;TEST @Value(autocad_layer) = SIGN~V~POT_JAL~PUB;TEST @Value(autocad_layer) = SIGN~V~POT_ROU~MAT;TEST @Value(autocad_layer) = SIGN~V~POT_ROU~00;TEST @Value(autocad_layer) = SIGN~V~POT~RUE;TEST @Value(autocad_layer) = SIGN~V~POT~BUS;TEST @Value(autocad_layer) = SIGN~V~POT~VILLE'P'FME_NUM_CONDITIONS3___
    -> AttributeFilter_5

Bookmark: HAB / Attribution FORME
Tester_26
    BOOL_OP = OR
    TEST_CLAUSE:
      TEST @Value(autocad_layer) = HAB~-~SENS~ESCA
      TEST @Value(autocad_layer) = HAB~-~SENS~SEUIL
    TEST_MODE = TEST
    PASSED -> AttributeCreator_19
AttributeCreator_19
    ATTR_TABLE = SET_TO FORME = P
    -> AttributeFilter_5

Bookmark: CR / Attribution FORME
Tester_6
    BOOL_OP = OR
    TEST_CLAUSE:
      TEST @Value(autocad_layer) = CR~LEVER~P~LEVE
      TEST @Value(autocad_layer) = CR~LEVER~P~PONCTUEL
    TEST_MODE = TEST
    PASSED -> AttributeCreator_22
AttributeCreator_22
    ATTR_TABLE = SET_TO FORME = FME_CONDITIONAL:DEFAULT_VALUE'_FME_NO_OP_'BOOL_OP;OR;COMPOSITE_TEST;<Unused>;TEST @Value(SSCLASSE) = LEVE'TL'BOOL_OP;OR;COMPOSITE_TEST;<Unused>;TEST @Value(SSCLASSE) = PONCTUEL'TP'FME_NUM_CONDITIONS3___
    -> AttributeFilter_5

Bookmark: Filtre /FORME
AttributeFilter_5
    ATTR_NAME = FORME
    ATTR_VALUES = <Empty>,<Missing>,<Null>,<Unfiltered>,L,S,TL,TP,PS_CAR,PS_CIR,PS_OVA,PS_REC,P,PL
    L -> Junction_175
    L -> Junction_32
    S -> Junction_21
    S -> Junction_32
    TL -> Junction_9
    TL -> Junction_32
    TP -> Junction_9
    TP -> Junction_32
    PS_CAR -> Junction_19
    PS_CAR -> Junction_32
    PS_CIR -> Junction_17
    PS_CIR -> Junction_32
    PS_OVA -> Junction_15
    PS_OVA -> Junction_32
    PS_REC -> Junction_13
    PS_REC -> Junction_32
    P -> Junction_11
    P -> Junction_32
    PL -> Junction_45
    PL -> Junction_32

Bookmark: Entrée + mise en forme
Note: vers récup info
Junction_32
    -> FeatureHolder

Bookmark: Recreation
FeatureHolder
    -> Tester_2
Note: DELIM~DP~PAR~-
Tester_2
    BOOL_OP = OR
    COMPOSITE_TEST = 1
    TEST_CLAUSE = TEST @Value(autocad_layer) = DELIM~DP~PAR~-
    TEST_MODE = TEST
    PASSED -> FeatureJoiner_5 [LEFT]
    FAILED -> FeatureJoiner [LEFT]
    FAILED -> FeatureJoiner_3 [LEFT]
reste_des_objets: FeatureHolder
    -> Junction_24
Junction_24
    -> Junction_23
Junction_23
    -> AttributeRemover

Bookmark: Tests Géometriques
Note: L
Junction_175
    -> Junction_146
Note: S
Junction_21
    -> Junction_14
Note: vers tests
Junction_14
    -> Junction_10
Note: TL/TP
Junction_9
    -> CoordinateExtractor_6
Note: PS_CAR
Junction_19
    -> Junction_167
Note: PS_CIR
Junction_17
    -> Junction_167
Note: PS_OVA
Junction_15
    -> Junction_167
Note: PS_REC
Junction_13
    -> Junction_167
Note: PL
Junction_45
    -> Junction_167
Note: P
Junction_11
    -> Junction_167
    -> Junction
Note: vers asso TP
Junction_167
    -> NeighborFinder_7 [BASE]
Junction_168
    -> Tester_31
Note: vers test DP
Junction

Bookmark: Entrées des données mises en forme
Note: surfaciques
Junction_10
    -> AttributeKeeper
AttributeKeeper
    KEEP_ATTRS = autocad_xscale_2,autocad_yscale,fme_feature_type_original,autocad_layer,autocad_block_name,TYPE,SSCLASSE,THEME,CLASSE,autocad_elevation,MAT,autocad_entity,ALT,FORME,SSTHEME,_IDOriginal,autocad_source_filename,fme_feature_type,autocad_xscale,autocad_rotation,autocad_yscale_2
    -> TestFilter
TestFilter
    DEFAULT_VALUE = <UNFILTERED>
    TEST_LIST = "BOOL_OP,OR,COMPOSITE_TEST,""""""1"""""",TEST_CLAUSE,TEST @Value(autocad_layer) = DELIM~DP~PAR~-",DELIM~DP~PAR~-
    DELIM~DP~PAR~- -> Junction_12
Note: points levés
Junction_156
    -> AttributeKeeper_9
AttributeKeeper_9
    KEEP_ATTRS = autocad_layer,_IDOriginal,autocad_yscale_2,fme_feature_type,autocad_xscale,autocad_rotation,autocad_xscale_2,FORME,THEME,_X,_z,LARG,CLASSE,SSTHEME,autocad_block_name,_x,autocad_entity,autocad_yscale,MAT,SSCLASSE,autocad_elevation,IDENT,LONG,ORIEN,TYPE,ALT,_Y,_y,NUM
    -> TestFilter_19
TestFilter_19
    DEFAULT_VALUE = <UNFILTERED>
    TEST_LIST = "BOOL_OP,OR,COMPOSITE_TEST,""""""1"""""",TEST_CLAUSE,TEST @Value(FORME) = TV",TV,"BOOL_OP,OR,COMPOSITE_TEST,""""""1"""""",TEST_CLAUSE,TEST @Value(FORME) = TL",TL,"BOOL_OP,OR,COMPOSITE_TEST,""""""1"""""",TEST_CLAUSE,TEST @Value(FORME) = TP",TP
    TL -> Junction_3
Note: linéaires
Junction_147
    -> AttributeKeeper_8
AttributeKeeper_8
    KEEP_ATTRS = autocad_layer,_IDOriginal,autocad_yscale_2,fme_feature_type,autocad_xscale,autocad_rotation,autocad_xscale_2,FORME,THEME,CLASSE,SSTHEME,autocad_block_name,autocad_entity,autocad_yscale,MAT,SSCLASSE,autocad_elevation,TYPE,ALT
    -> Junction_44
Note: ponctuel surfaciques
Junction_145
    -> AttributeKeeper_6
AttributeKeeper_6
    KEEP_ATTRS = CLASSE,autocad_block_name,autocad_elevation,TYPE,autocad_xscale_2,THEME,MAT,fme_feature_type,autocad_xscale,autocad_layer,FORME,IDENT,SSCLASSE,autocad_entity,autocad_yscale,autocad_yscale_2,autocad_rotation,ALT,SSTHEME
    -> Junction_4

Bookmark: Tables de relations
Note: depuis surfacique
Junction_12
    -> AttributeRenamer_3
Note: _IDOriginal_PAR
AttributeRenamer_3
    ATTR_TABLE = RENAME_SET_DEFAULT _IDOriginal > _IDOriginal_PAR
    -> GeometryCoercer_4
Note: depuis TL
Junction_3
    -> AttributeRenamer
Note: _IDOriginal_TL
AttributeRenamer
    ATTR_TABLE = RENAME_SET_DEFAULT _IDOriginal > _IDOriginal_TL
    -> FeatureHolder_3
Note: depuis linéaires
Junction_44
    -> AttributeRenamer_2
Note: _IDOriginal_lineaire
AttributeRenamer_2
    ATTR_TABLE = RENAME_SET_DEFAULT _IDOriginal > _IDOriginal_lineaire
    -> Tester_4
Note: DP~DEC/CAD
Tester_4
    BOOL_OP = OR
    COMPOSITE_TEST = 1 OR 2
    TEST_CLAUSE:
      TEST @Value(autocad_layer) = DELIM~DP~LIM~DEC
      TEST @Value(autocad_layer) = DELIM~DP~LIM~CAD
    TEST_MODE = TEST
    PASSED -> Chopper
    PASSED -> Clipper_2 [CLIPPEE]
    FAILED -> lineaire
Note: depuis ponctuels surfaciques
Junction_4
    -> PS

Bookmark: Test PAR
GeometryCoercer_4
    GQUERY:
      for $geom in //geometry
      where $geom/count(parent::geometry) = 0
      return number($geom/@fme_id)
    KIND = fme_line
    COERCED -> Counter_8
Note: _IDLigne
Counter_8
    CNT_ATTR = _IDLigne
    DOMAIN = IDLigne
    SCOPE = Global
    START = 0
    -> AttributeKeeper_11
AttributeKeeper_11
    KEEP_ATTRS = autocad_layer,_IDOriginal_PAR,_IDLigne
    -> Clipper_3 [CLIPPEE]
Note: XYZ_TL
AttributeCreator_2
    ATTR_TABLE = SET_TO XYZ_TL = @Value(_x)_@Value(_y)_@Value(_z)
    -> AttributeKeeper_12
AttributeKeeper_12
    KEEP_ATTRS = XYZ_TL,_IDOriginal_TL,_z,NUM
    -> Bufferer_2
    -> NeighborFinder_3 [BASE]
Note: Buff 0.01m
Bufferer_2
    ANGLE = 22.5
    CAP_STYLE = Round
    CORNER_STYLE = Round
    MODE = AREA
    OFFSET = 0.01
    OFFSET_UNITS = NONE
    BUFFERED -> Clipper_3 [CLIPPER]
Note: TL cherche linéaires (à 0.005m)
NeighborFinder_3
    CANDIDATES_FIRST = No
    CLOSE_LIST_ATTRS_TO_INCLUDE = _IDFrag _IDLigne _mean_Z_frag autocad_layer XYZ_ligne _IDOriginal_PAR
    CLOSE_LIST_ATTRS_TO_INCLUDE_MODE = Selected Attributes
    CLOSE_LIST_NAME = list_lineaire
    INSERT_VERTEX = No
    MAX = 0.005
    MEASURES_FROM_CANDIDATE = No
    MEASURE_TYPE = Continuous
    MODE = Bases and Candidates
    TREAT_POLYGON_AS = Lines
    MATCHED -> ListExploder_3
ListExploder_3
    ATTR_ACCUM_MODE = Merge List Attributes
    ATTR_CONFLICT_RES = Use List Attribute Values
    INDEX_ATTR = _element_index
    LIST_ATTR = list_lineaire{}
    ELEMENTS -> Tester_7
Note: Coord du TL dans liste coord linéaire?
Tester_5
    BOOL_OP = OR
    COMPOSITE_TEST = 1
    TEST_CLAUSE = CASE_INSENSITIVE_TEST @Value(XYZ_ligne) CONTAINS @Value(XYZ_TL)
    TEST_MODE = CASE_INSENSITIVE_TEST
    FAILED -> AttributeCreator_197
    FAILED -> Junction_25

Bookmark: Vérif. points TL/TP
Note: valeur de Z donné à ALT
CoordinateExtractor_6
    IND = 0
    MODE = Specify Coordinate
    Z_ATTR = ALT
    -> TestFilter_3
    -> TestFilter_4
Note: Point Ponctuel
TestFilter_4
    DEFAULT_VALUE = <UNFILTERED>
    TEST_LIST:
      "BOOL_OP,AND,COMPOSITE_TEST,""""""<Unused>"""""",TEST_CLAUSE,TEST @Value(FORME) = TP
      TEST @Value(ALT) > 0",TP correct,"BOOL_OP,OR,COMPOSITE_TEST,""""""<Unused>"""""",TEST_CLAUSE,TEST @Value(FORME) = TP",TP mauvaise ALT
    TP correct -> Counter
    TP mauvaise ALT -> Counter
Counter
    CNT_ATTR = IDENT
    DOMAIN = IDENT
    SCOPE = Global
    START = 1
    -> CoordinateExtractor_3
CoordinateExtractor_3
    IND = 0
    MODE = Specify Coordinate
    X_ATTR = _X
    Y_ATTR = _Y
    Z_ATTR = ALT
    -> AttributeRounder_5
AttributeRounder_5
    PLACES = 5
    ROUND_TYPE = Nearest
    SRC_ATTRS = _X _Y ALT
    -> Matcher_14
Matcher_14
    BLANK_AND_MISSING_DIFFER = No
    CHECK_TYPES_AND_ENCODINGS = No
    CNT_ATTR = _match_id
    MATCHATTRS = _X _Y ALT
    MATCH_STRATEGY = Match Selected Attributes
    SINGLE_MATCHED -> Junction_59
    SINGLE_MATCHED -> NeighborFinder_8 [BASE]
    SINGLE_MATCHED -> NeighborFinder_7 [CANDIDATE]
    NOT_MATCHED -> NeighborFinder_7 [CANDIDATE]
    NOT_MATCHED -> Junction_59
    NOT_MATCHED -> NeighborFinder_8 [BASE]
Note: vers asso vertex PL
Junction_59
Note: Point Levé
TestFilter_3
    DEFAULT_VALUE = <UNFILTERED>
    TEST_LIST:
      "BOOL_OP,AND,COMPOSITE_TEST,""""""<Unused>"""""",TEST_CLAUSE,TEST @Value(FORME) = TL
      TEST @Value(ALT) > 0",TL correct,"BOOL_OP,OR,COMPOSITE_TEST,""""""<Unused>"""""",TEST_CLAUSE,TEST @Value(FORME) = TL",TL mauvaise ALT
    TL correct -> CoordinateExtractor_4
    TL mauvaise ALT -> CoordinateExtractor_4

Bookmark: TL dupli en x,y,z?
CoordinateExtractor_4
    IND = 0
    MODE = Specify Coordinate
    X_ATTR = _x
    Y_ATTR = _y
    Z_ATTR = _z
    -> AttributeRounder_4
AttributeRounder_4
    PLACES = 3
    ROUND_TYPE = Nearest
    SRC_ATTRS = _x _y _z
    -> Matcher_15
Matcher_15
    BLANK_AND_MISSING_DIFFER = No
    CHECK_TYPES_AND_ENCODINGS = No
    CNT_ATTR = _match_id
    MATCHATTRS = _y _x _z
    MATCH_STRATEGY = Match Selected Attributes
    SINGLE_MATCHED -> Counter_2
    NOT_MATCHED -> Counter_2

Bookmark: Asso. blocs avec points TP (1 par bloc)
NeighborFinder_7
    CANDIDATES_FIRST = No
    CLOSE_LIST_ATTRS_TO_INCLUDE = ALT
    CLOSE_LIST_ATTRS_TO_INCLUDE_MODE = Selected Attributes
    CLOSE_LIST_NAME = _info
    INSERT_VERTEX = No
    K = 1
    MAX = 0.01
    MEASURES_FROM_CANDIDATE = Yes
    MEASURE_TYPE = Continuous
    MODE = Bases and Candidates
    TREAT_POLYGON_AS = Lines
    MATCHED -> Tester_31
    MATCHED -> NeighborFinder_8 [CANDIDATE]
    UNMATCHED_BASE -> Tester_34
    UNMATCHED_BASE -> NeighborFinder_8 [CANDIDATE]

Bookmark: Asso. points TP avec blocs (1 par TP)
Note: sortie TPs
NeighborFinder_8
    CANDIDATES_FIRST = No
    CLOSE_LIST_ATTRS_TO_INCLUDE = CLASSE FORME SSCLASSE SSTHEME THEME autocad_rotation autocad_xscale autocad_yscale
    CLOSE_LIST_ATTRS_TO_INCLUDE_MODE = Selected Attributes
    CLOSE_LIST_NAME = Info
    INSERT_VERTEX = No
    K = 1
    MAX = 0.01
    MEASURES_FROM_CANDIDATE = Yes
    MEASURE_TYPE = Continuous
    MODE = Bases and Candidates
    TREAT_POLYGON_AS = Lines
    MATCHED -> AttributeCreator_27

Bookmark: Récup. des att du bloc
AttributeCreator_27
    ATTR_TABLE:
      SET_TO THEME = @Value(Info{0}.THEME)
      SET_TO SSTHEME = @Value(Info{0}.SSTHEME)
      SET_TO CLASSE = @Value(Info{0}.CLASSE)
      SET_TO SSCLASSE = @Value(Info{0}.SSCLASSE)
      SET_TO LONG = @Value(Info{0}.autocad_xscale)
      SET_TO LARG = @Value(Info{0}.autocad_yscale)
      SET_TO ORIEN = @Value(Info{0}.autocad_rotation)
    -> Tester_35

Bookmark: Bloc asso. est Ponctuel?
Tester_35
    BOOL_OP = OR
    TEST_CLAUSE = TEST @Value(Info{0}.FORME) = P
    TEST_MODE = TEST
    FAILED -> Counter_2

Bookmark: Créa. att. NUM sur TL et TP(sur Ponctuel)
Counter_2
    CNT_ATTR = NUM
    DOMAIN = NUM
    SCOPE = Global
    START = 1
    -> Tester_38

Bookmark: block_name = PointTopoL?
Tester_38
    BOOL_OP = OR
    TEST_CLAUSE = TEST @Value(autocad_block_name) = PointTopoL
    TEST_MODE = TEST
    PASSED -> Junction_155
    FAILED -> Junction_155

Bookmark: Points Lever
Note: vers tests d'Asso
Junction_155
    -> Junction_156
    -> __TL
__TL: Inspector

Bookmark: Filtre TL
Note: TL
FeatureHolder_3
    -> NeighborFinder_47 [BASE]
PS: FeatureHolder
    -> Tester_158
Note: COF ou ARM?
Tester_158
    BOOL_OP = COMPOSITE
    COMPOSITE_TEST = 1 AND ( 2 OR 3 )
    TEST_CLAUSE:
      TEST @Value(THEME) = RESEAU
      TEST @Value(CLASSE) = ARM
      TEST @Value(CLASSE) = COF
    TEST_MODE = TEST
    PASSED -> NeighborFinder_47 [CANDIDATE]
Note: TL non asso aux COF et ARM
NeighborFinder_47
    CANDIDATES_FIRST = No
    INSERT_VERTEX = No
    MAX = 0.01
    MEASURES_FROM_CANDIDATE = No
    MEASURE_TYPE = Continuous
    MODE = Bases and Candidates
    TREAT_POLYGON_AS = Lines
    UNMATCHED_BASE -> AttributeCreator_196
    UNMATCHED_BASE -> NeighborFinder_2 [BASE]

Bookmark: Bloc ss TP: PL?
Tester_34
    BOOL_OP = OR
    TEST_CLAUSE = TEST @Value(FORME) = PL
    TEST_MODE = TEST
    PASSED -> Tester_31
    FAILED -> Tester_3

Bookmark: Bloc ss TP: AMOR?
Tester_3
    BOOL_OP = OR
    TEST_CLAUSE = TEST @Value(autocad_layer) = DELIM~DP~AMOR~-
    TEST_MODE = TEST
    FAILED -> Tester_108

Bookmark: Test: objet surf relevé en ligne?
Tester_108
    BOOL_OP = COMPOSITE
    COMPOSITE_TEST = 1 AND 2
    TEST_CLAUSE:
      TEST @Value(autocad_entity) = autocad_polygon
      TEST @Value(SSCLASSE) = CIR
    TEST_MODE = TEST
    PASSED -> Junction_168
    FAILED -> Junction_168

Bookmark: Test: PS?
Tester_31
    BOOL_OP = OR
    TEST_CLAUSE:
      TEST @Value(FORME) = PS_CAR
      TEST @Value(FORME) = PS_CIR
      TEST @Value(FORME) = PS_OVA
      TEST @Value(FORME) = PS_REC
    TEST_MODE = TEST
    PASSED -> CoordinateExtractor_2
    FAILED -> Tester_39

Bookmark: Test: PL?
Tester_39
    BOOL_OP = OR
    TEST_CLAUSE = TEST @Value(FORME) = PL
    TEST_MODE = TEST
    PASSED -> Junction_47
Junction_47
    -> Junction_48

Bookmark: Objets Linéaires
Note: PL filtré depuis surf.
Junction_48
    -> Junction_146
Note: vers tests d'Asso
Junction_146
    -> Junction_147

Bookmark: TL proche de linéaire test si il appartient aux coordonnées du linéaire
lineaire: FeatureHolder
    -> Counter_34
Note: _IDLigne
Counter_34
    CNT_ATTR = _IDLigne
    DOMAIN = IDLigne
    SCOPE = Global
    START = 0
    -> GeometryCoercer_6
Note: transfo en ligne
GeometryCoercer_6
    GQUERY:
      for $geom in //geometry
      where $geom/count(parent::geometry) = 0
      return number($geom/@fme_id)
    KIND = fme_line
    COERCED -> AttributeKeeper_28
AttributeKeeper_28
    KEEP_ATTRS = autocad_layer,_IDLigne,_IDOriginal_lineaire
    -> Clipper_6 [CLIPPEE]
Note: XYZ_TL
AttributeCreator_196
    ATTR_TABLE = SET_TO XYZ_TL = @Value(_x)_@Value(_y)_@Value(_z)
    -> AttributeKeeper_27
AttributeKeeper_27
    KEEP_ATTRS = XYZ_TL,_z,NUM,_IDOriginal_TL
    -> Bufferer_4
    -> NeighborFinder_46 [BASE]
Note: Buff 0.01m
Bufferer_4
    ANGLE = 22.5
    CAP_STYLE = Round
    CORNER_STYLE = Round
    MODE = AREA
    OFFSET = 0.01
    OFFSET_UNITS = NONE
    BUFFERED -> Clipper_6 [CLIPPER]
Note: TL cherche linéaires (à 0.005m)
NeighborFinder_46
    CANDIDATES_FIRST = No
    CLOSE_LIST_ATTRS_TO_INCLUDE = _IDFrag _IDLigne _mean_Z_frag autocad_layer XYZ_ligne _IDOriginal_lineaire
    CLOSE_LIST_ATTRS_TO_INCLUDE_MODE = Selected Attributes
    CLOSE_LIST_NAME = list_lineaire
    INSERT_VERTEX = No
    MAX = 0.005
    MEASURES_FROM_CANDIDATE = No
    MEASURE_TYPE = Continuous
    MODE = Bases and Candidates
    TREAT_POLYGON_AS = Lines
    MATCHED -> ListExploder_23
ListExploder_23
    ATTR_ACCUM_MODE = Merge List Attributes
    ATTR_CONFLICT_RES = Use List Attribute Values
    INDEX_ATTR = _element_index
    LIST_ATTR = list_lineaire{}
    ELEMENTS -> Tester_159
Note: Coord du TL dans liste coord linéaire?
Tester_157
    BOOL_OP = OR
    COMPOSITE_TEST = 1
    TEST_CLAUSE = CASE_INSENSITIVE_TEST @Value(XYZ_ligne) CONTAINS @Value(XYZ_TL)
    TEST_MODE = CASE_INSENSITIVE_TEST
    FAILED -> AttributeCreator_197
    FAILED -> Junction_2

Bookmark: Filtre TL le long de DEC et CAD (en plus de filtre sur COF/ARM)
Note: sommets des DEC/CAD
Chopper
    DEAGGREGATE_INPUT = Deaggregate
    MAX_VERTICES = 1
    MODE = By Vertex
    CHOPPED -> Bufferer_3
Note: Buff 0.01m
Bufferer_3
    ANGLE = 22.5
    CAP_STYLE = Round
    CORNER_STYLE = Round
    MODE = AREA
    OFFSET = 0.01
    OFFSET_UNITS = NONE
    BUFFERED -> Clipper_2 [CLIPPER]
Note: segments sans extrem
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> NeighborFinder_2 [CANDIDATE]
Note: TL non asso aux segments DEC et CAD
NeighborFinder_2
    CANDIDATES_FIRST = No
    INSERT_VERTEX = No
    MAX = 0.01
    MEASURES_FROM_CANDIDATE = No
    MEASURE_TYPE = Continuous
    MODE = Bases and Candidates
    TREAT_POLYGON_AS = Lines
    UNMATCHED_BASE -> AttributeCreator_2

Bookmark: Vérif. PS duppli. en X,Y par calque
CoordinateExtractor_2
    IND = 0
    MODE = Specify Coordinate
    X_ATTR = X
    Y_ATTR = Y
    -> AttributeCreator_74
Note: X,Y rounder
AttributeCreator_74
    ATTR_TABLE:
      SET_TO Xround = @Evaluate(@round(@Value(X),2))
      SET_TO Yround = @Evaluate(@round(@Value(Y),2))
    -> Matcher_17
Note: mm X,Y et layer
Matcher_17
    BLANK_AND_MISSING_DIFFER = No
    CHECK_TYPES_AND_ENCODINGS = No
    CNT_ATTR = _match_id
    MATCHATTRS = Xround Yround autocad_layer
    MATCH_STRATEGY = Match Selected Attributes
    MATCHED -> AttributeRemover_2
    NOT_MATCHED -> Matcher_16

Bookmark: Objets Surafciques
Note: mm X,Y ; layer diff.
Note: vers linéaire
Matcher_16
    BLANK_AND_MISSING_DIFFER = No
    CHECK_TYPES_AND_ENCODINGS = No
    CNT_ATTR = _match_id
    DIFFATTRS = autocad_layer
    MATCHATTRS = Xround Yround
    MATCH_STRATEGY = Match Selected Attributes
    MATCHED -> AttributeRemover_2
    NOT_MATCHED -> AttributeRemover_2
AttributeRemover_2
    REMOVE_ATTRS = Yround,Xround
    -> AttributeCreator_23
__Objet_surfacique: Inspector
Note: vers test d'Asso
Junction_142
    -> Junction_145
Note: vers lignes ctrl DP
Junction_39
Note: vers DP
Junction_5

Bookmark: Créa. att. ALT
AttributeCreator_23
    ATTR_TABLE = SET_TO ALT = @Value(_info{0}.ALT)
    -> 2DEllipseReplacer_2

Bookmark: Transfo. en ellipse
2DEllipseReplacer_2
    PRIMAXIS = @Value(autocad_xscale)/2
    ROT = 0
    SECAXIS = @Value(autocad_yscale)/2
    XVALATTR = @Value(X)
    YVALATTR = @Value(Y)
    ELLIPSE -> Tester_32

Bookmark: Test forme: cercle(CIR)?
Tester_32
    BOOL_OP = COMPOSITE
    COMPOSITE_TEST = 1
    TEST_CLAUSE = TEST @Value(FORME) = PS_CIR
    TEST_MODE = TEST
    PASSED -> Tester_105
    FAILED -> Tester_33

Bookmark: Test: objet surf relevé en ligne?
Tester_105
    BOOL_OP = OR
    COMPOSITE_TEST = 1
    TEST_CLAUSE = TEST @Value(autocad_entity) = autocad_polygon
    TEST_MODE = TEST
    PASSED -> Counter_4
    FAILED -> 3DForcer_2

Bookmark: Test forme: ovale(OVA)?
Tester_33
    BOOL_OP = OR
    TEST_CLAUSE = CASE_INSENSITIVE_TEST @Value(FORME) CONTAINS PS_OVA
    TEST_MODE = TEST
    PASSED -> Rotator_3
    FAILED -> BoundsExtractor_2

Bookmark: Appli. rotation origi.
Rotator_3
    ANGLE = @Value(autocad_rotation)
    XORIG = @Value(X)
    YORIG = @Value(Y)
    ROTATED -> 3DForcer_2
Rotator_4
    ANGLE = @Value(autocad_rotation)
    XORIG = @Value(X)
    YORIG = @Value(Y)
    ROTATED -> 3DForcer_2

Bookmark: Donc carré(CAR) ou rectangle(REC) -> miseF.
BoundsExtractor_2
    XMAX = _xmax
    XMIN = _xmin
    YMAX = _ymax
    YMIN = _ymin
    -> 2DBoxReplacer_2
2DBoxReplacer_2
    MAXXVALATTR = @Value(_xmax)
    MAXYVALATTR = @Value(_ymax)
    MINXVALATTR = @Value(_xmin)
    MINYVALATTR = @Value(_ymin)
    BOX -> Rotator_4

Bookmark: Appli. de l'ALT
3DForcer_2
    KEEPZVAL = No
    ZVALATTR = @Value(ALT)
    -> Counter_4
    <REJECTED> -> Counter_4

Bookmark: Créa. IDENT
Counter_4
    CNT_ATTR = IDENT
    DOMAIN = IDENT
    SCOPE = Global
    START = 1
    -> Tester_112
    -> __Objet_surfacique

Bookmark: Filtre blocs defectueux
Note: Blocs pouvant êtres defect.
Tester_112
    BOOL_OP = COMPOSITE
    COMPOSITE_TEST = 1 OR 2 OR 3 OR 4 OR 5 OR 6 OR 7 OR 8 OR 9 OR 10 OR 11 OR ( 12 AND ( 13 OR 14 OR 15 OR 16 ) AND ( 17 OR 18 OR 19 OR 20 ))
    TEST_CLAUSE:
      TEST @Value(autocad_layer) = MOB~URB~BANC~-
      TEST @Value(autocad_layer) = DELIM~CLOT~PIL~CAR
      TEST @Value(autocad_layer) = DELIM~CLOT~PIL~REC
      TEST @Value(autocad_layer) = NATURE~VERT~BAC~REC
      TEST @Value(autocad_layer) = RESEAU~ASSA~AVA~00
      TEST @Value(autocad_layer) = RESEAU~ASSA~AVA~D
      TEST @Value(autocad_layer) = RESEAU~ASSA~AVA~G
      TEST @Value(autocad_layer) = RESEAU~ASSA~AVA~GRILLE
      TEST @Value(autocad_layer) = RESEAU~ASSA~AVA~RE_GR
      TEST @Value(autocad_layer) = RESEAU~ASSA~AVA~REGARD
      TEST @Value(autocad_layer) = RESEAU~ASSA~GRIL~REC
      TEST @Value(THEME) = RESEAU
      TEST @Value(CLASSE) = COF
      TEST @Value(CLASSE) = ARM
      TEST @Value(CLASSE) = PLA
      TEST @Value(CLASSE) = REG
      TEST @Value(SSCLASSE) = 00
      TEST @Value(SSCLASSE) = ENCA
      TEST @Value(SSCLASSE) = CAR
      TEST @Value(SSCLASSE) = REC
    TEST_MODE = TEST
    PASSED -> Junction_135
    FAILED -> FeatureHolder_4
Note: vers test blocs defect.
Junction_135
    -> Junction_136
Note: retour test blocs defect.
Junction_138
    -> FeatureHolder_4
FeatureHolder_4
    -> Junction_39
    -> Junction_5
    -> Junction_142

Bookmark: Integration de la geom des blocs potentiellement defectueux
Note: PS créé selon x,y_scales
Junction_136
    -> AttributeCreator_191
Note: Récup de l'info original de fme_feature_type
AttributeCreator_191
    ATTR_TABLE = SET_TO fme_feature_type = @Value(fme_feature_type_original)
    -> SpatialFilter [Candidate]
Note: Buffer 0.01m
Note: Blocs qui correspondent à la géom de leur version explo -> vers sortie ...
SpatialFilter
    AGGREGATE_HANDLING = Yes
    BASE_TYPE = Multiple Filters
    CURVE_BOUNDARY_RULE_PARAM = Default Rule
    GROUP_BY = fme_feature_type
    PASS_CRITERIA = Pass Against One Filter
    PREDICATES = CONTAINS
    USE_BOUNDING_BOX = No
    PASSED -> FeatureHolder_5
    FAILED -> SpatialFilter_2 [Filter]
Note: ... Blocs qui ne correspondent pas -> leur géom remplacée par celle de la version explo
SpatialFilter_2
    AGGREGATE_HANDLING = Yes
    ATTR_ACCUM_MODE = Merge Filter
    ATTR_CONFLICT_RES = Use Candidate
    BASE_TYPE = Multiple Filters
    CURVE_BOUNDARY_RULE_PARAM = Default Rule
    GROUP_BY = fme_feature_type
    PASS_CRITERIA = Pass Against One Filter
    PREDICATES = INTERSECTS
    USE_BOUNDING_BOX = No
    PASSED -> FeatureHolder_5
FeatureHolder_5
    -> Junction_137
Note: retour suite des ctrl
Junction_137
    -> Junction_138
__Bloc_explo: Inspector

Bookmark: Chrono
Note: depuis Start
Junction_118
    -> DateTimeStamper
Note: Start
DateTimeStamper
    DATETIME_ATTR = _timestampStart
    INCLUDE_OFFSET = NO
    STAMP_TYPE = datetime
    TIMEZONE = local
    -> AttributeKeeper_4
AttributeKeeper_4
    KEEP_ATTRS = _timestampStart
    -> Sorter_4
Sorter_4
    SORT_PARM = _timestampStart NUMERIC ASCENDING
    SORTED -> Sampler_4
Sampler_4
    RATE = 1
    SAMPLE_MODE = No
    SAMPLE_TYPE_LONG = First N Features
    SAMPLED -> AttributeCreator_70
Note: Cle
AttributeCreator_70
    ATTR_TABLE = SET_TO Cle = 1
    -> FeatureMerger_14 [SUPPLIER]
Note: Finish
DateTimeStamper_2
    DATETIME_ATTR = _timestampFinish
    INCLUDE_OFFSET = NO
    STAMP_TYPE = datetime
    TIMEZONE = local
    -> AttributeCreator_71
Note: Cle
AttributeCreator_71
    ATTR_TABLE = SET_TO Cle = 1
    -> FeatureMerger_14 [REQUESTOR]
FeatureMerger_14
    ATTR_ACCUM_MODE = Merge Supplier
    ATTR_CONFLICT_RES = Use Requestor
    IGNORE_NULLS = No
    JOIN_KEYS = @Value(Cle) @Value(Cle) AUTO
    MERGE_TYPE = Attributes Only
    PROCESS_DUPS = NO
    REJECT_NULL_MISSING_KEYS = No
    SUPPLIERS_FIRST = No
    MERGED -> AttributeCreator_72
Note: Calcul Running time
AttributeCreator_72
    ATTR_TABLE = SET_TO Running time (in min) = @Evaluate(@round(@DateTimeDiff(@Value(_timestampFinish),@Value(_timestampStart),minutes),0))
    -> stat_rapport_erreur (writer XLSXW_1)

Bookmark: Entrée des versions explo des blocs
Note: Entrée blocs potentiellement defectueux en version explo
0 (reader ACAD_2)
    -> AttributeSplitter_2
AttributeSplitter_2
    ATTR_NAME = fme_feature_type
    DELIMITER = ~
    DROP_EMPTY_PARTS = No
    LIST_NAME = _description
    TRIM_OPTION = Both
    -> AttributeCreator_119
AttributeCreator_119
    ATTR_TABLE:
      SET_TO THEME = @Value(_description{0})
      SET_TO SSTHEME = @Value(_description{1})
      SET_TO CLASSE = @Value(_description{2})
      SET_TO SSCLASSE = @Value(_description{3})
    -> AttributeExposer_2
AttributeExposer_2
    ATTR_LIST = autocad_entity
    -> VertexCounter_3
VertexCounter_3
    CNT_ATTR = _coordcount
    -> Tester_113
Tester_113
    BOOL_OP = OR
    COMPOSITE_TEST = 1
    TEST_CLAUSE = TEST @Value(autocad_entity) = autocad_surface
    TEST_MODE = TEST
    PASSED -> GeometryCoercer_2
    FAILED -> TestFilter_15
Note: surfaces en poly
GeometryCoercer_2
    GQUERY:
      for $geom in //geometry
      where $geom/count(parent::geometry) = 0
      return number($geom/@fme_id)
    KIND = fme_polygon
    COERCED -> AttributeCreator_123
AttributeCreator_123
    ATTR_TABLE = SET_TO autocad_entity = autocad_polygon
    -> VertexCounter_4
VertexCounter_4
    CNT_ATTR = _coordcount
    -> TestFilter_15
TestFilter_15
    DEFAULT_VALUE = <UNFILTERED>
    TEST_LIST:
      "BOOL_OP,AND,COMPOSITE_TEST,""""""1 AND 2 AND 3"""""",TEST_CLAUSE,TEST @Value(fme_feature_type) = MOB~URB~BANC~-
      TEST @Value(_coordcount) = 5
      TEST @Value(autocad_entity) = autocad_polygon",MOB~URB~BANC~-,"BOOL_OP,COMPOSITE,COMPOSITE_TEST,""""""( 1 OR 2 ) AND 3 AND 4"""""",TEST_CLAUSE,TEST @Value(fme_feature_type) = DELIM~CLOT~PIL~CAR
      TEST @Value(fme_feature_type) = DELIM~CLOT~PIL~REC
      TEST @Value(_coordcount) = 5
      TEST @Value(autocad_entity) = autocad_polygon",DELIM~CLOT~PIL~CAR et REC,"BOOL_OP,COMPOSITE,COMPOSITE_TEST,""""""1 AND 2 AND 3 AND 4 AND ( 5 OR 6 )"""""",TEST_CLAUSE,TEST @Value(THEME) = RESEAU
      TEST @Value(SSCLASSE) = ENCA
      TEST @Value(_coordcount) = 5
      TEST @Value(autocad_entity) = autocad_polygon
      TEST @Value(CLASSE) = COF
      TEST @Value(CLASSE) = ARM",COF ou ARM ENCA,"BOOL_OP,AND,COMPOSITE_TEST,""""""1 AND 2 AND 3"""""",TEST_CLAUSE,TEST @Value(fme_feature_type) = RESEAU~ASSA~AVA~REGARD
      TEST @Value(_coordcount) = 5
      TEST @Value(autocad_entity) = autocad_polygon",RESEAU~ASSA~AVA~REGARD,"BOOL_OP,AND,COMPOSITE_TEST,""""""1 AND 2 AND 3"""""",TEST_CLAUSE,TEST @Value(fme_feature_type) = RESEAU~ASSA~GRIL~REC
      TEST @Value(_coordcount) = 5
      TEST @Value(autocad_entity) = autocad_polygon",RESEAU~ASSA~GRIL~REC,"BOOL_OP,AND,COMPOSITE_TEST,""""""1 AND 2 AND 3"""""",TEST_CLAUSE,TEST @Value(fme_feature_type) = RESEAU~ASSA~AVA~00
      TEST @Value(_coordcount) = 5
      TEST @Value(autocad_entity) = autocad_polygon",RESEAU~ASSA~AVA~00,"BOOL_OP,COMPOSITE,COMPOSITE_TEST,""""""( 1 OR 2 ) AND 3 AND 4"""""",TEST_CLAUSE,TEST @Value(fme_feature_type) = RESEAU~ASSA~AVA~G
      TEST @Value(fme_feature_type) = RESEAU~ASSA~AVA~D
      TEST @Value(_coordcount) = 7
      TEST @Value(autocad_entity) = autocad_polygon",RESEAU~ASSA~AVA~G/D,"BOOL_OP,AND,COMPOSITE_TEST,""""""1 AND 2"""""",TEST_CLAUSE,TEST @Value(fme_feature_type) = NATURE~VERT~BAC~REC
      TEST @Value(autocad_entity) = autocad_polygon",NATURE~VERT~BAC~REC forme poly,"BOOL_OP,OR,COMPOSITE_TEST,""""""1"""""",TEST_CLAUSE,TEST @Value(fme_feature_type) = NATURE~VERT~BAC~REC",NATURE~VERT~BAC~REC autres,"BOOL_OP,COMPOSITE,COMPOSITE_TEST,""""""1 AND 2 AND 3 AND ( 4 OR 5 )"""""",TEST_CLAUSE,TEST @Value(THEME) = RESEAU
      TEST @Value(_coordcount) = 5
      TEST @Value(autocad_entity) = autocad_polygon
      TEST @Value(CLASSE) = COF
      TEST @Value(CLASSE) = ARM",COF ou ARM,"BOOL_OP,COMPOSITE,COMPOSITE_TEST,""""""1 AND 2 AND 3 AND ( 4 OR 5 )"""""",TEST_CLAUSE,TEST @Value(THEME) = RESEAU
      TEST @Value(_coordcount) = 5
      TEST @Value(autocad_entity) = autocad_polygon
      TEST @Value(CLASSE) = PLA
      TEST @Value(CLASSE) = REG",PLA ou REG
    MOB~URB~BANC~- -> FeatureHolder_6
    DELIM~CLOT~PIL~CAR et REC -> FeatureHolder_6
    COF ou ARM ENCA -> FeatureHolder_6
    RESEAU~ASSA~AVA~REGARD -> FeatureHolder_6
    RESEAU~ASSA~GRIL~REC -> FeatureHolder_6
    RESEAU~ASSA~AVA~00 -> FeatureHolder_6
    RESEAU~ASSA~AVA~G/D -> FeatureHolder_6
    NATURE~VERT~BAC~REC forme poly -> FeatureHolder_6
    NATURE~VERT~BAC~REC autres -> SpatialRelator_5 [Requestor]
    NATURE~VERT~BAC~REC autres -> SpatialRelator_5 [Supplier]
    COF ou ARM -> FeatureHolder_6
    PLA ou REG -> FeatureHolder_6
FeatureHolder_6
    -> AttributeRemover_4
AttributeRemover_4
    LIST_ATTRS = _description{}
    REMOVE_ATTRS = _coordcount,autocad_entity
    -> SpatialFilter_2 [Candidate]
    -> Bufferer
    -> __Bloc_explo
Bufferer
    ANGLE = 22.5
    CAP_STYLE = Round
    CORNER_STYLE = Round
    MODE = AREA
    OFFSET = 0.01
    OFFSET_UNITS = NONE
    BUFFERED -> SpatialFilter [Filter]

Bookmark: REC exterieur NATURE~VERT~BAC~REC
SpatialRelator_5
    AGGREGATE_HANDLING = Yes
    CALC_CARD = No
    CURVE_BOUNDARY_RULE_PARAM = Default Rule
    PREDICATES = CONTAINS
    SUCCESS_ATTR = _related_candidates
    -> Tester_104
Tester_104
    BOOL_OP = OR
    COMPOSITE_TEST = 1
    TEST_CLAUSE = TEST @Value(_related_candidates) = 3
    TEST_MODE = TEST
    PASSED -> FeatureHolder_6

Bookmark: Test selon buffer autour du TL
Clipper_6
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Counter_35
Note: _IDFrag
Counter_35
    CNT_ATTR = _IDFrag
    DOMAIN = IDFrag
    SCOPE = Global
    START = 0
    -> CoordinateExtractor_29
    -> FeatureJoiner_22 [LEFT]
    -> AttributeKeeper_25
FeatureJoiner_22
    ATTR_CONFLICT_RES = Use Left
    GEOMETRY_HANDLING = Use Left
    JOIN_KEYS = _IDFrag _IDFrag AUTO
    JOIN_MODE = Inner
    JOINED -> FeatureJoiner_23 [LEFT]
FeatureJoiner_23
    ATTR_CONFLICT_RES = Use Left
    GEOMETRY_HANDLING = Use Left
    JOIN_KEYS = _IDFrag _IDFrag AUTO
    JOIN_MODE = Inner
    JOINED -> NeighborFinder_46 [CANDIDATE]

Bookmark: TL récup infos Z pour test proxi en Z de ligne
CoordinateExtractor_29
    LIST_NAME = _coord_frag
    MODE = All Coordinates
    -> ListExploder_24
ListExploder_24
    ATTR_ACCUM_MODE = Merge List Attributes
    ATTR_CONFLICT_RES = Use List Attribute Values
    INDEX_ATTR = _element_index
    LIST_ATTR = _coord_frag{}
    ELEMENTS -> StatisticsCalculator_11
StatisticsCalculator_11
    COMPUTE_HISTOGRAM = NO
    GROUP_BY = _IDFrag
    MEAN_ATTR = _mean_Z_frag
    PREPEND_ATTR_NAME_CHOICE = For multiple results only
    STATS_ATTRS = z
    SUMMARY -> AttributeRounder_22
AttributeRounder_22
    PLACES = 2
    ROUND_TYPE = Nearest
    SRC_ATTRS = _mean_Z_frag
    -> FeatureJoiner_22 [RIGHT]

Bookmark: Récup coords linéaire
AttributeKeeper_25
    KEEP_ATTRS = autocad_layer,_IDFrag
    -> CoordinateExtractor_27
Note: _coord_lineaire
CoordinateExtractor_27
    LIST_NAME = _coord_lineaire
    MODE = All Coordinates
    -> ListExploder_22
ListExploder_22
    ATTR_ACCUM_MODE = Merge List Attributes
    ATTR_CONFLICT_RES = Use List Attribute Values
    INDEX_ATTR = _element_index
    LIST_ATTR = _coord_lineaire{}
    ELEMENTS -> AttributeRounder_19
AttributeRounder_19
    PLACES = 3
    ROUND_TYPE = Nearest
    SRC_ATTRS = x y z
    -> AttributeCreator_194
Note: XYZ_ligne
AttributeCreator_194
    ATTR_TABLE = SET_TO XYZ_ligne = @Value(x)_@Value(y)_@Value(z)
    -> Aggregator_2
Aggregator_2
    ACCUM_ATTRS_NAME = Use Attributes From One Feature
    AGGREGATE_TYPE = Homogeneous Collection (If Possible)
    CONCAT_ATTRS = XYZ_ligne
    GROUP_BY = _IDFrag
    MODE = Geometry - Assemble One Level
    SEP = /
    AGGREGATE -> AttributeCreator_195
AttributeCreator_195
    ATTR_TABLE = SET_TO XYZ_ligne = /@Value(XYZ_ligne)/
    -> AttributeKeeper_26
AttributeKeeper_26
    KEEP_ATTRS = XYZ_ligne,_IDFrag
    -> FeatureJoiner_23 [RIGHT]

Bookmark: Test proxi Z
Tester_159
    BOOL_OP = COMPOSITE
    COMPOSITE_TEST = 1 AND 2
    TEST_CLAUSE:
      TEST @Value(_z) >= @Evaluate(@Value(_mean_Z_frag)-0.01)
      TEST @Value(_z) <= @Evaluate(@Value(_mean_Z_frag)+0.01)
    TEST_MODE = TEST
    PASSED -> Tester_157

Bookmark: Preparation
Note: objets TP/linéaire créant erreur vers recréation
Junction_2
    -> Junction_6
Note: objets TP/PAR créant erreur vers recréation
Junction_25
    -> Junction_26

Bookmark: Créa liste zones concernées (TL/linéaires)
Note: objets créant erreur
Junction_6
    -> AttributeKeeper_7
    -> AttributeKeeper_10
Note: TL (test linéaire)
AttributeKeeper_7
    KEEP_ATTRS = _IDOriginal_TL
    -> Sampler
Sampler
    GROUP_BY = _IDOriginal_TL
    RATE = 1
    SAMPLE_MODE = No
    SAMPLE_TYPE_LONG = First N Features
    SAMPLED -> FeatureJoiner [RIGHT]
    SAMPLED -> CoordinateExtractor_5
CoordinateExtractor_5
    IND = 0
    MODE = Specify Coordinate
    X_ATTR = _x_Anchor
    Y_ATTR = _y_Anchor
    Z_ATTR = _z_Anchor
    -> Junction_20
Note: vers ref 3D
Junction_20
    -> Junction_16
Note: Linéaires
AttributeKeeper_10
    KEEP_ATTRS = _IDOriginal_lineaire
    -> Sampler_2
Sampler_2
    GROUP_BY = _IDOriginal_lineaire
    RATE = 1
    SAMPLE_MODE = No
    SAMPLE_TYPE_LONG = First N Features
    SAMPLED -> FeatureJoiner_2 [RIGHT]

Bookmark: Appli Z du TL sur PAR
Note: TL base Anchor
Junction_16
    -> NeighborFinder_80 [CANDIDATE]
Counter_7
    CNT_ATTR = IDENT_LIN
    DOMAIN = IDENT_LIN
    SCOPE = Global
    START = 0
    -> Chopper_20
Chopper_20
    DEAGGREGATE_INPUT = Deaggregate
    MAX_VERTICES = 1
    MODE = By Vertex
    REMNANT_ATTR = _remnant
    CHOPPED -> Counter_16
Note: Découpe ligne et créa indice
Counter_16
    CNT_ATTR = _index
    DOMAIN = counter_@Value(IDENT_LIN)
    SCOPE = Global
    START = 0
    -> CoordinateExtractor_67
CoordinateExtractor_67
    IND = 0
    MODE = Specify Coordinate
    X_ATTR = Coord_X
    Y_ATTR = Coord_Y
    Z_ATTR = Coord_Z
    -> NeighborFinder_80 [BASE]
Note: Nouveau vertex cherche sa vrai Anchor
NeighborFinder_80
    CANDIDATES_FIRST = No
    CLOSE_LIST_ATTRS_TO_INCLUDE = _x_Anchor _y_Anchor _z_Anchor
    CLOSE_LIST_ATTRS_TO_INCLUDE_MODE = Selected Attributes
    CLOSE_LIST_NAME = _list_anchors_
    INSERT_VERTEX = No
    MAX = 0.0001
    MEASURES_FROM_CANDIDATE = No
    MEASURE_TYPE = Continuous
    MODE = Bases and Candidates
    TREAT_POLYGON_AS = Lines
    MATCHED -> AttributeCreator_161
    UNMATCHED_BASE -> Junction_280
Note: IDENT_index
AttributeCreator_161
    ATTR_TABLE = SET_TO IDENT_index = @Value(IDENT_LIN)_@Value(_index)
    -> ListExploder_17
ListExploder_17
    ATTR_ACCUM_MODE = Merge List Attributes
    ATTR_CONFLICT_RES = Use List Attribute Values
    INDEX_ATTR = _element_index
    LIST_ATTR = _list_anchors_{}
    ELEMENTS -> AttributeCreator_25
Note: Round_Coord_Z / Round_z_Anchor
AttributeCreator_25
    ATTR_TABLE:
      SET_TO Round_Coord_Z = @Value(Coord_Z)
      SET_TO Round_z_Anchor = @Value(_z_Anchor)
    -> AttributeRounder_7
AttributeRounder_7
    PLACES = 2
    ROUND_TYPE = Nearest
    SRC_ATTRS = Round_z_Anchor Round_Coord_Z
    -> Tester_143
Note: Anchor dans la tolérance du snap en Z?
Tester_143
    BOOL_OP = COMPOSITE
    COMPOSITE_TEST = 1 AND 2
    TEST_CLAUSE:
      TEST @Value(Round_Coord_Z) >= @Evaluate(@Value(Round_z_Anchor)-0.01)
      TEST @Value(Round_Coord_Z) <= @Evaluate(@Value(Round_z_Anchor)+0.01)
    TEST_MODE = TEST
    PASSED -> Sampler_25
    FAILED -> Sampler_26
Note: 1 vertex par IDENT_index
Sampler_25
    GROUP_BY = IDENT_index
    RATE = 1
    SAMPLE_MODE = No
    SAMPLE_TYPE_LONG = First N Features
    SAMPLED -> VertexCreator_16
    SAMPLED -> AttributeCreator_163
Note: Copie des IDENT_index renseignés en Z pour stopper les aurtes sans asso
AttributeCreator_163
    ATTR_TABLE = SET_TO STOP = Yes
    -> Matcher_37
Note: Récup coord du vrai Anchor
VertexCreator_16
    MEASURE_TYPE = Continuous
    MODE_NAME = Replace with Point
    XVAL = @Value(_x_Anchor)
    YVAL = @Value(_y_Anchor)
    ZVAL = @Value(_z_Anchor)
    -> Junction_280
Note: 1 vertex par IDENT_index
Sampler_26
    GROUP_BY = IDENT_index
    RATE = 1
    SAMPLE_MODE = No
    SAMPLE_TYPE_LONG = First N Features
    SAMPLED -> Matcher_37
Matcher_37
    BLANK_AND_MISSING_DIFFER = No
    CHECK_TYPES_AND_ENCODINGS = No
    CNT_ATTR = _match_id
    MATCHATTRS = IDENT_index
    MATCH_STRATEGY = Match Selected Attributes
    NOT_MATCHED -> Tester_144
Note: STOP = Yes?
Tester_144
    BOOL_OP = OR
    COMPOSITE_TEST = 1
    TEST_CLAUSE = TEST @Value(STOP) = Yes
    TEST_MODE = TEST
    FAILED -> Junction_280
Junction_280
    -> Sorter_10

Bookmark: Traitement linéaires
Note: TL concerné par erreur
FeatureJoiner
    ATTR_CONFLICT_RES = Use Left
    GEOMETRY_HANDLING = Use Left
    JOIN_KEYS = _IDOriginal _IDOriginal_TL AUTO
    JOIN_MODE = Inner
    JOINED -> AnchoredSnapper [ANCHOR]
    JOINED -> reste_des_objets
    UNJOINED_LEFT -> FeatureJoiner_2 [LEFT]
Note: linéaire concerné par erreur
FeatureJoiner_2
    ATTR_CONFLICT_RES = Use Left
    GEOMETRY_HANDLING = Use Left
    JOIN_KEYS = _IDOriginal _IDOriginal_lineaire AUTO
    JOIN_MODE = Inner
    JOINED -> AnchoredSnapper [CANDIDATE]
    UNJOINED_LEFT -> reste_des_objets
Note: Asso linéaires avec TL du test linéaire
AnchoredSnapper
    CLEANING_TOLERANCE = Automatic
    SNAPTYPE_PARAM = Segment Snapping
    TOLERANCE = 0.01
    SNAPPED -> Junction_7
    UNTOUCHED -> Junction_7
Junction_7
    -> Counter_7

Bookmark: Reconstru ligne incluant les Anchors
Sorter_10
    SORT_PARM = _index NUMERIC ASCENDING
    SORTED -> LineBuilder_6
LineBuilder_6
    ACCUM_INPUT_ATTRS = Use Attributes From One Feature
    GROUP_BY = IDENT_LIN
    REMOVE_DUPLICATES = No
    LINE -> FeatureHolder_32
    POLYGON -> GeometryCoercer_9
GeometryCoercer_9
    GQUERY:
      for $geom in //geometry
      where $geom/count(parent::geometry) = 0
      return number($geom/@fme_id)
    KIND = fme_line
    COERCED -> FeatureHolder_32
    UNTOUCHED -> FeatureHolder_32
Note: Linéaire vers sortie
FeatureHolder_32
    -> Junction_23

Bookmark: Test selon buffer autour du TL
Clipper_3
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Counter_9
Note: _IDFrag
Counter_9
    CNT_ATTR = _IDFrag
    DOMAIN = IDFrag
    SCOPE = Global
    START = 0
    -> CoordinateExtractor_8
    -> FeatureJoiner_7 [LEFT]
    -> AttributeKeeper_13
FeatureJoiner_7
    ATTR_CONFLICT_RES = Use Left
    GEOMETRY_HANDLING = Use Left
    JOIN_KEYS = _IDFrag _IDFrag AUTO
    JOIN_MODE = Inner
    JOINED -> FeatureJoiner_8 [LEFT]
FeatureJoiner_8
    ATTR_CONFLICT_RES = Use Left
    GEOMETRY_HANDLING = Use Left
    JOIN_KEYS = _IDFrag _IDFrag AUTO
    JOIN_MODE = Inner
    JOINED -> NeighborFinder_3 [CANDIDATE]

Bookmark: TL récup infos Z pour test proxi en Z de ligne
CoordinateExtractor_8
    LIST_NAME = _coord_frag
    MODE = All Coordinates
    -> ListExploder_4
ListExploder_4
    ATTR_ACCUM_MODE = Merge List Attributes
    ATTR_CONFLICT_RES = Use List Attribute Values
    INDEX_ATTR = _element_index
    LIST_ATTR = _coord_frag{}
    ELEMENTS -> StatisticsCalculator_2
StatisticsCalculator_2
    COMPUTE_HISTOGRAM = NO
    GROUP_BY = _IDFrag
    MEAN_ATTR = _mean_Z_frag
    PREPEND_ATTR_NAME_CHOICE = For multiple results only
    STATS_ATTRS = z
    SUMMARY -> AttributeRounder_3
AttributeRounder_3
    PLACES = 2
    ROUND_TYPE = Nearest
    SRC_ATTRS = _mean_Z_frag
    -> FeatureJoiner_7 [RIGHT]

Bookmark: Récup coords linéaire
AttributeKeeper_13
    KEEP_ATTRS = autocad_layer,_IDFrag
    -> CoordinateExtractor_7
Note: _coord_lineaire
CoordinateExtractor_7
    LIST_NAME = _coord_lineaire
    MODE = All Coordinates
    -> ListExploder_2
ListExploder_2
    ATTR_ACCUM_MODE = Merge List Attributes
    ATTR_CONFLICT_RES = Use List Attribute Values
    INDEX_ATTR = _element_index
    LIST_ATTR = _coord_lineaire{}
    ELEMENTS -> AttributeRounder_2
AttributeRounder_2
    PLACES = 3
    ROUND_TYPE = Nearest
    SRC_ATTRS = x y z
    -> AttributeCreator_3
Note: XYZ_ligne
AttributeCreator_3
    ATTR_TABLE = SET_TO XYZ_ligne = @Value(x)_@Value(y)_@Value(z)
    -> Aggregator_3
Aggregator_3
    ACCUM_ATTRS_NAME = Use Attributes From One Feature
    AGGREGATE_TYPE = Homogeneous Collection (If Possible)
    CONCAT_ATTRS = XYZ_ligne
    GROUP_BY = _IDFrag
    MODE = Geometry - Assemble One Level
    SEP = /
    AGGREGATE -> AttributeCreator_4
AttributeCreator_4
    ATTR_TABLE = SET_TO XYZ_ligne = /@Value(XYZ_ligne)/
    -> AttributeKeeper_14
AttributeKeeper_14
    KEEP_ATTRS = XYZ_ligne,_IDFrag
    -> FeatureJoiner_8 [RIGHT]

Bookmark: Test proxi Z
Tester_7
    BOOL_OP = COMPOSITE
    COMPOSITE_TEST = 1 AND 2
    TEST_CLAUSE:
      TEST @Value(_z) >= @Evaluate(@Value(_mean_Z_frag)-0.01)
      TEST @Value(_z) <= @Evaluate(@Value(_mean_Z_frag)+0.01)
    TEST_MODE = TEST
    PASSED -> Tester_5

Bookmark: CHECK: Line not connect to TL
AttributeCreator_197
    ATTR_TABLE:
      SET_TO ERREUR = Line_not_connect_to_TL_(@Value(autocad_layer))
      SET_TO autocad_layer = Erreur
    -> Line_not_connect_to_TL
    -> Tester
Note: GO_sortie_erreurs
Tester
    BOOL_OP = OR
    COMPOSITE_TEST = 1
    TEST_CLAUSE = TEST $(GO_sortie_erreurs) = Yes
    TEST_MODE = TEST
    PASSED -> Junction_125
Note: erreurs vers sortie
Junction_125
    -> Junction_126
Line_not_connect_to_TL: Inspector

Bookmark: Sortie
Junction_126
    -> GeometryValidator_3
AttributeKeeper_5
    KEEP_ATTRS = FORME,SSCLASSE,autocad_rotation,fme_feature_type,autocad_block_name,Missing,autocad_entity,THEME,autocad_xscale,autocad_yscale,autocad_elevation,autocad_layer,Alerte,CLASSE,SSTHEME,ERREUR
    -> VertexCounter_2

Bookmark: Correction coord. ERROR fausses
GeometryValidator_3
    ISSUE_ATTR_NAME = _issues
    PRESETS = Custom
    REPAIR = Yes
    RULES = NAN_REMOVAL PROCESS_MEASURE]NO]FME_CONTROLLER_QUERY_FILE]transformers\dependencies\geometryvalidator\NAN_REMOVAL.fme
    SUMMARY = Detailed
    PASSED -> Clipper [CLIPPEE]
    PASSED -> Aggregator
    INVALID_PARTS -> 3DForcer_4
Note: Appli. d'un Z = 1 pour les annonces avec Z corrompu
3DForcer_4
    KEEPZVAL = No
    ZVALATTR = 1
    -> Clipper [CLIPPEE]
    -> Aggregator

Bookmark: Box
Aggregator
    ACCUM_ATTRS_NAME = Use Attributes From One Feature
    AGGREGATE_TYPE = Homogeneous Collection (If Possible)
    ATTR_TO_TRAIT = Yes
    ID_SELECTION = ID and Parent ID
    MODE = Geometry - Assemble One Level
    ORDERED = No
    PRESERVE_ID = No
    SEP = ,
    AGGREGATE -> BoundsExtractor
BoundsExtractor
    XMAX = _xmax
    YMAX = _ymax
    -> AttributeKeeper_3
AttributeKeeper_3
    KEEP_ATTRS = _ymax,_xmax
    -> GeometryRemover_2
GeometryRemover_2
    -> VertexCreator_9
Note: Vertex_bas_gauche
VertexCreator_9
    MODE_NAME = Add Point
    XVAL = 200
    YVAL = 0
    -> VertexCreator_10
Note: Vertex_haut_droit
VertexCreator_10
    MODE_NAME = Add Point
    XVAL = @Value(_xmax)+200
    YVAL = @Value(_ymax)+200
    -> BoundingBoxReplacer
BoundingBoxReplacer
    BOXTYPE = 2D Bounding Box
    BOX -> Clipper [CLIPPER]

Bookmark: Conservation des error dans la box
Clipper
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> AttributeKeeper_5
    INSIDE -> CenterPointReplacer_10

Bookmark: Conversion erreur en point
VertexCounter_2
    CNT_ATTR = _coordcount
    -> Tester_64
Note: 1 vertex?
Tester_64
    BOOL_OP = OR
    TEST_CLAUSE = TEST @Value(_coordcount) = 1
    TEST_MODE = TEST
    PASSED -> CenterPointExtractor_4
    FAILED -> Snipper_13
Note: Ligne? Récup point central
Snipper_13
    DEAGGREGATE_INPUT = YES
    ENDLOCATIONATTR = 50
    MEASUREMENTTYPE = 2D
    SNIPMODE = Distance (Percentage)
    STARTLOCATIONATTR = 50
    -> CenterPointExtractor_4
    <REJECTED> -> Snipper_14
Snipper_14
    DEAGGREGATE_INPUT = YES
    ENDVERTEXATTR = 1
    SNIPMODE = Vertex
    STARTVERTEXATTR = 1
    -> CenterPointExtractor_4
    <REJECTED> -> CenterPointReplacer_9
CenterPointReplacer_9
    MODE = Center of Gravity Point
    POINT -> CenterPointExtractor_4
CenterPointExtractor_4
    CENTX = _inside_x
    CENTY = _inside_y
    CENTZ = _inside_z
    MODE = Center
    -> AttributeRounder_8
AttributeRounder_8
    PLACES = 3
    ROUND_TYPE = Nearest
    SRC_ATTRS = _inside_x _inside_y
    -> Matcher_18

Bookmark: Multi buffer pour repré des erreurs superposées
Note: Superpo. err trait nouv. err?
Matcher_18
    BLANK_AND_MISSING_DIFFER = No
    CHECK_TYPES_AND_ENCODINGS = No
    CNT_ATTR = _match_id
    DIFFATTRS = ERROR_traitee
    MATCHATTRS = _inside_y ERREUR _inside_x
    MATCH_STRATEGY = Match Selected Attributes
    MATCHED -> Tester_97
    NOT_MATCHED -> Matcher_11
Note: Err. trait a priorité
Tester_97
    BOOL_OP = OR
    COMPOSITE_TEST = 1
    TEST_CLAUSE = TEST @Value(ERROR_traitee) = Oui
    TEST_MODE = TEST
    PASSED -> Matcher_11
Note: Erreurs superposées?
Matcher_11
    BLANK_AND_MISSING_DIFFER = No
    CNT_ATTR = _match_id
    LENIENT_MATCH = No
    MATCH = NONE
    MATCHATTRS = _inside_x _inside_y
    MATCH_STRATEGY = Match Selected Attributes
    MATCHED -> Counter_12
    NOT_MATCHED -> AttributeCreator_75
Note: Counter par matchId
Counter_12
    CNT_ATTR = _MultiBuff
    DOMAIN = @Value(_match_id)
    SCOPE = Global
    START = 10
    -> 2DEllipseReplacer_3
AttributeCreator_75
    ATTR_TABLE = SET_TO _MultiBuff = 10
    -> 2DEllipseReplacer_3

Bookmark: Crea. cercle
2DEllipseReplacer_3
    PRIMAXIS = 0.2*@Value(_MultiBuff)
    ROT = 0
    SECAXIS = 0.2*@Value(_MultiBuff)
    XVALATTR = @Value(_inside_x)
    YVALATTR = @Value(_inside_y)
    ELLIPSE -> AttributeCreator_98
Note: autocad_entity = ellipse
AttributeCreator_98
    ATTR_TABLE = SET_TO autocad_entity = autocad_ellipse
    -> AttributeManager_9
AttributeManager_9
    ATTR_TABLE:
      SET_TO ERREUR = CHECK~@Value(ERREUR)
      REMOVE ALT
      REMOVE THEME
      REMOVE CLASSE
      REMOVE SSCLASSE
      REMOVE TYPE
      REMOVE MAT
      REMOVE _description{}
      REMOVE autocad_xscale_2
      REMOVE autocad_yscale_2
    -> AttributeCreator_34
Note: Scales=1
AttributeCreator_34
    ATTR_TABLE:
      SET_TO autocad_xscale = 1
      SET_TO autocad_yscale = 1
      SET_TO autocad_zscale = 1
    -> TestFilter_14
TestFilter_14
    DEFAULT_VALUE = Erreur
    TEST_LIST = "BOOL_OP,OR,COMPOSITE_TEST,""""""1"""""",TEST_CLAUSE,TEST @Value(ERROR_traitee) = Oui",Erreur_traitee
    Erreur_traitee -> Junction_35
    Erreur -> DWGStyler_2
Note: Erreurs traitée réintégrées vers DWG en sortie
Junction_35
    -> Junction_36
Note: Style erreur
DWGStyler_2
    AREA_TYPE_LONG = MPolygon With Fill Pattern
    BLOCK_ROT = 0
    BLOCK_SIZETYPE_DISPLAY = Scale Factor
    BLOCK_SIZEX = 1.0
    BLOCK_SIZEY = 1.0
    BLOCK_SIZEZ = 1.0
    COLOR = 0,0.666667,1
    FILL_PATTERN = SOLID
    LINE_PATTERNING = Continuous
    LINE_SCALE = 1.0
    LINE_WIDTH = 50
    TEMPLATE_FILE = $(SourceDataset_ACAD)
    DWGStyled -> DateTimeStamper_4

Bookmark: Sortie
Note: Erreurs traitée réintégrées vers DWG en sortie
Junction_36
    -> RESEAU~SLT~BOUCLE~FEU (writer ACAD_4)
RESEAU~SLT~BOUCLE~FEU (writer ACAD_4)
    attributes: ALT number(7,4), TYPE char(2), MAT number(6,0)

Bookmark: TimeStamp
DateTimeStamper_4
    DATETIME_ATTR = _timestamp2
    STAMP_TYPE = date
    TIMEZONE = local
    -> AttributeCreator_73
Note: Découpe _timestamp
AttributeCreator_73
    ATTR_TABLE:
      SET_TO Annee2 = @Left(@Value(_timestamp2),4)
      SET_TO Mois2 = @Right(@Left(@Value(_timestamp2),6),2)
      SET_TO Jour2 = @Right(@Left(@Value(_timestamp2),8),2)
      SET_TO Date2 = @Value(Jour2)_@Value(Mois2)_@Value(Annee2)
    -> RESEAU~SLT~BOUCLE~FEU (writer ACAD_3)

Bookmark: Sortie ERROR ALERTE
RESEAU~SLT~BOUCLE~FEU (writer ACAD_3)
    attributes: Annee2 char(200), Mois2 char(200), Jour2 char(200), Date2 char(200), ERREUR char(200), _match_id char(200), _MultiBuff number(20,0), _coordcount number(20,0), fme_rejection_code string, ERROR_traitee char(200), _inside_x char(200), _inside_y char(200), _inside_z char(200), fme_feature_type_original char(50), _IDOriginal number(20,0), autocad_source_filename string, _filename string, _timestamp2 string

Bookmark: Récup. coord. ERROR
CenterPointReplacer_10
    MODE = Center Point
    POINT -> AttributeKeeper_2

Bookmark: Sortie tableau stat d'erreur
AttributeKeeper_2
    KEEP_ATTRS = Missing,MAT,Alerte,ERROR_traitee,ERREUR
    -> AttributeCreator_99
Note: MiseF erreurs avec descri.
AttributeCreator_99
    ATTR_TABLE = SET_TO ERREUR = FME_CONDITIONAL:DEFAULT_VALUE'@Value(ERREUR)'BOOL_OP;OR;COMPOSITE_TEST;1;CASE_INSENSITIVE_TEST @Value(ERREUR) CONTAINS Non joined line'@Left(@Value(ERREUR),15)'BOOL_OP;OR;COMPOSITE_TEST;1;CASE_INSENSITIVE_TEST @Value(ERREUR) CONTAINS Duplicate line'@Left(@Value(ERREUR),14)'BOOL_OP;OR;COMPOSITE_TEST;1;CASE_INSENSITIVE_TEST @Value(ERREUR) CONTAINS Duplicate surface'@Left(@Value(ERREUR),17)'BOOL_OP;OR;COMPOSITE_TEST;1;CASE_INSENSITIVE_TEST @Value(ERREUR) CONTAINS Wrong Geometry'@Left(@Value(ERREUR),14)'BOOL_OP;OR;COMPOSITE_TEST;1;CASE_INSENSITIVE_TEST @Value(ERREUR) CONTAINS Left_rule_line_on_left_rule_line_but_opposed_direction'@Left(@Value(ERREUR),54)'BOOL_OP;OR;COMPOSITE_TEST;1;CASE_INSENSITIVE_TEST @Value(ERREUR) CONTAINS Right_rule_line_on_right_rule_line_but_opposed_direction'@Left(@Value(ERREUR),56)'BOOL_OP;OR;COMPOSITE_TEST;1;CASE_INSENSITIVE_TEST @Value(ERREUR) CONTAINS Left_rule_line_on_right_rule_line_but_same_direction'@Left(@Value(ERREUR),52)'BOOL_OP;OR;COMPOSITE_TEST;1;CASE_INSENSITIVE_TEST @Value(ERREUR) CONTAINS Unknow_layer_from_Template_called'@Left(@Value(ERREUR),26)'BOOL_OP;OR;COMPOSITE_TEST;1;CASE_INSENSITIVE_TEST @Value(ERREUR) CONTAINS Line_not_connect_to_TL'@Left(@Value(ERREUR),22)'FME_NUM_CONDITIONS10___
    -> Tester_98
Note: ERROR_traitee=Oui
Tester_98
    BOOL_OP = OR
    COMPOSITE_TEST = 1
    TEST_CLAUSE = TEST @Value(ERROR_traitee) = Oui
    TEST_MODE = TEST
    PASSED -> FeatureCounter_2
    FAILED -> FeatureCounter
Note: Compte erreurs traitées
FeatureCounter_2
    FeatureCounterNewAttrParameter = Nombre_erreur_traitees
    GROUP_BY = ERREUR
    -> FeatureJoiner_4 [RIGHT]
Note: Compte nouvelles erreurs
FeatureCounter
    FeatureCounterNewAttrParameter = Nombre_erreurs_total
    GROUP_BY = ERREUR
    -> FeatureJoiner_4 [LEFT]
FeatureJoiner_4
    ATTR_CONFLICT_RES = Use Left
    GEOMETRY_HANDLING = Use Left
    JOIN_KEYS = ERREUR ERREUR AUTO
    JOIN_MODE = Inner
    JOINED -> AttributeCreator_111
    UNJOINED_LEFT -> AttributeCreator_110
Note: Nombre_erreurs_traitees=0
AttributeCreator_110
    ATTR_TABLE = SET_TO Nombre_erreur_traitees = 0
    -> AttributeCreator_111
Note: Nombre_erreurs_restantes
AttributeCreator_111
    ATTR_TABLE = SET_TO Nombre_erreurs_restantes = @Evaluate(@Value(Nombre_erreurs_total)-@Value(Nombre_erreur_traitees))
    -> Sampler_3
Sampler_3
    GROUP_BY = ERREUR
    RATE = 1
    SAMPLE_MODE = No
    SAMPLE_TYPE_LONG = First N Features
    SAMPLED -> DateTimeStamper_3
DateTimeStamper_3
    DATETIME_ATTR = _timestamp
    STAMP_TYPE = date
    TIMEZONE = local
    -> AttributeCreator_54
Note: Découpe _timestamp
AttributeCreator_54
    ATTR_TABLE:
      SET_TO Annee = @Left(@Value(_timestamp),4)
      SET_TO Mois = @Right(@Left(@Value(_timestamp),6),2)
      SET_TO Jour = @Right(@Left(@Value(_timestamp),8),2)
      SET_TO Date = @Value(Jour)_@Value(Mois)_@Value(Annee)
    -> AttributeCreator_124
Note: NAME, TYPE, Ordre
AttributeCreator_124
    ATTR_TABLE:
      SET_TO NAME = @Value(ERREUR)
      SET_TO TYPE = Check
      SET_TO Ordre = FME_CONDITIONAL:DEFAULT_VALUE'_FME_NO_OP_'BOOL_OP;OR;COMPOSITE_TEST;1;TEST @Value(TYPE) = Error'1'BOOL_OP;OR;COMPOSITE_TEST;1;TEST @Value(TYPE) = Missing'2'BOOL_OP;OR;COMPOSITE_TEST;1;TEST @Value(TYPE) = Alerte'3'FME_NUM_CONDITIONS4___
    -> Sorter_3
Sorter_3
    SORT_PARM = Ordre NUMERIC ASCENDING Nombre_erreurs_total NUMERIC DESCENDING
    SORTED -> DateTimeStamper_2
stat_rapport_erreur (writer XLSXW_1)
    attributes: Date string(20), Running time (in min) auto(20), TYPE auto(40), NAME auto(50), Nombre_erreurs_total auto(20), Nombre_erreur_traitees auto(40), Nombre_erreurs_restantes auto(40)

Bookmark: Créa liste zones concernées (TL/PAR)
Note: objets créant erreur
Junction_26
    -> AttributeKeeper_15
    -> AttributeKeeper_16
Note: TL (test PAR)
AttributeKeeper_15
    KEEP_ATTRS = _IDOriginal_TL
    -> Sampler_5
Sampler_5
    GROUP_BY = _IDOriginal_TL
    RATE = 1
    SAMPLE_MODE = No
    SAMPLE_TYPE_LONG = First N Features
    SAMPLED -> CoordinateExtractor_9
    SAMPLED -> FeatureJoiner_3 [RIGHT]
CoordinateExtractor_9
    IND = 0
    MODE = Specify Coordinate
    X_ATTR = _x_Anchor
    Y_ATTR = _y_Anchor
    Z_ATTR = _z_Anchor
    -> Junction_27
Note: vers ref 3D
Junction_27
    -> Junction_22
Note: PAR
AttributeKeeper_16
    KEEP_ATTRS = _IDOriginal_PAR
    -> Sampler_6
Sampler_6
    GROUP_BY = _IDOriginal_PAR
    RATE = 1
    SAMPLE_MODE = No
    SAMPLE_TYPE_LONG = First N Features
    SAMPLED -> FeatureJoiner_5 [RIGHT]

Bookmark: Appli Z du TL sur PAR
Note: TL base Anchor
Junction_22
    -> NeighborFinder_52 [CANDIDATE]
Counter_6
    CNT_ATTR = IDENT_PAR
    DOMAIN = IDENT_PAR
    SCOPE = Global
    START = 0
    -> Chopper_19
Chopper_19
    DEAGGREGATE_INPUT = Deaggregate
    MAX_VERTICES = 1
    MODE = By Vertex
    REMNANT_ATTR = _remnant
    CHOPPED -> Counter_15
Note: Découpe surf et créa indice
Counter_15
    CNT_ATTR = _index
    DOMAIN = counter_@Value(IDENT_PAR)
    SCOPE = Global
    START = 0
    -> CoordinateExtractor_66
CoordinateExtractor_66
    IND = 0
    MODE = Specify Coordinate
    X_ATTR = Coord_X
    Y_ATTR = Coord_Y
    Z_ATTR = Coord_Z
    -> NeighborFinder_52 [BASE]
Note: Nouveau vertex cherche sa vrai Anchor
NeighborFinder_52
    CANDIDATES_FIRST = No
    CLOSE_LIST_ATTRS_TO_INCLUDE = _x_Anchor _y_Anchor _z_Anchor
    CLOSE_LIST_ATTRS_TO_INCLUDE_MODE = Selected Attributes
    CLOSE_LIST_NAME = _list_anchors_
    INSERT_VERTEX = No
    MAX = 0.0001
    MEASURES_FROM_CANDIDATE = No
    MEASURE_TYPE = Continuous
    MODE = Bases and Candidates
    TREAT_POLYGON_AS = Lines
    MATCHED -> AttributeCreator_162
    UNMATCHED_BASE -> Junction_18
Note: IDENT_index
AttributeCreator_162
    ATTR_TABLE = SET_TO IDENT_index = @Value(IDENT_PAR)_@Value(_index)
    -> ListExploder_10
ListExploder_10
    ATTR_ACCUM_MODE = Merge List Attributes
    ATTR_CONFLICT_RES = Use List Attribute Values
    INDEX_ATTR = _element_index
    LIST_ATTR = _list_anchors_{}
    ELEMENTS -> AttributeCreator_28
Note: Round_Coord_Z / Round_z_Anchor
AttributeCreator_28
    ATTR_TABLE:
      SET_TO Round_Coord_Z = @Value(Coord_Z)
      SET_TO Round_z_Anchor = @Value(_z_Anchor)
    -> AttributeRounder_10
AttributeRounder_10
    PLACES = 2
    ROUND_TYPE = Nearest
    SRC_ATTRS = Round_z_Anchor Round_Coord_Z
    -> Tester_109
Note: Anchor dans la tolérance du snap en Z?
Tester_109
    BOOL_OP = COMPOSITE
    COMPOSITE_TEST = 1 AND 2
    TEST_CLAUSE:
      TEST @Value(Round_Coord_Z) >= @Evaluate(@Value(Round_z_Anchor)-0.01)
      TEST @Value(Round_Coord_Z) <= @Evaluate(@Value(Round_z_Anchor)+0.01)
    TEST_MODE = TEST
    PASSED -> Sampler_16
    FAILED -> Sampler_24
Note: 1 vertex par IDENT_index
Sampler_16
    GROUP_BY = IDENT_index
    RATE = 1
    SAMPLE_MODE = No
    SAMPLE_TYPE_LONG = First N Features
    SAMPLED -> VertexCreator_15
    SAMPLED -> AttributeCreator_150
Note: Copie des IDENT_index renseignés en Z pour stopper les aurtes sans asso
AttributeCreator_150
    ATTR_TABLE = SET_TO STOP = Yes
    -> Matcher_38
Note: Récup coord du vrai Anchor
VertexCreator_15
    MEASURE_TYPE = Continuous
    MODE_NAME = Replace with Point
    XVAL = @Value(_x_Anchor)
    YVAL = @Value(_y_Anchor)
    ZVAL = @Value(_z_Anchor)
    -> Junction_18
Note: 1 vertex par IDENT_index
Sampler_24
    GROUP_BY = IDENT_index
    RATE = 1
    SAMPLE_MODE = No
    SAMPLE_TYPE_LONG = First N Features
    SAMPLED -> Matcher_38
Matcher_38
    BLANK_AND_MISSING_DIFFER = No
    CHECK_TYPES_AND_ENCODINGS = No
    CNT_ATTR = _match_id
    MATCHATTRS = IDENT_index
    MATCH_STRATEGY = Match Selected Attributes
    NOT_MATCHED -> Tester_142
Note: STOP = Yes?
Tester_142
    BOOL_OP = OR
    COMPOSITE_TEST = 1
    TEST_CLAUSE = TEST @Value(STOP) = Yes
    TEST_MODE = TEST
    FAILED -> Junction_18
Junction_18
    -> Sorter_9

Bookmark: Traitement surfacique
Note: TL concerné par erreur
FeatureJoiner_3
    ATTR_CONFLICT_RES = Use Left
    GEOMETRY_HANDLING = Use Left
    JOIN_KEYS = _IDOriginal _IDOriginal_TL AUTO
    JOIN_MODE = Inner
    JOINED -> AnchoredSnapper_2 [ANCHOR]
Note: PAR concerné par erreur
FeatureJoiner_5
    ATTR_CONFLICT_RES = Use Left
    GEOMETRY_HANDLING = Use Left
    JOIN_KEYS = _IDOriginal _IDOriginal_PAR AUTO
    JOIN_MODE = Inner
    JOINED -> AnchoredSnapper_2 [CANDIDATE]
    UNJOINED_LEFT -> reste_des_objets
Note: Asso PAR avec TL du test PAR
AnchoredSnapper_2
    CLEANING_TOLERANCE = Automatic
    SNAPTYPE_PARAM = Segment Snapping
    TOLERANCE = 0.01
    SNAPPED -> Junction_8
    UNTOUCHED -> Junction_8
Junction_8
    -> Counter_6

Bookmark: Reconstru ligne incluant les Anchors
Sorter_9
    SORT_PARM = _index NUMERIC ASCENDING
    SORTED -> LineBuilder_3
LineBuilder_3
    ACCUM_INPUT_ATTRS = Use Attributes From One Feature
    GROUP_BY = IDENT_PAR
    REMOVE_DUPLICATES = No
    LINE -> LineCloser_7
    POLYGON -> GeometryCoercer_3
LineCloser_7
    CONNECT_Z_MODE = First Wins
    AREA -> FeatureHolder_30
GeometryCoercer_3
    GQUERY:
      for $geom in //geometry
      where $geom/count(parent::geometry) = 0
      return number($geom/@fme_id)
    KIND = fme_line
    COERCED -> FeatureHolder_30
FeatureHolder_30
    -> GeometryCoercer_8
Note: Transfo en polygone
GeometryCoercer_8
    GQUERY:
      for $geom in //geometry
      where $geom/count(parent::geometry) = 0
      return number($geom/@fme_id)
    KIND = fme_polygon
    COERCED -> Junction_104
    UNTOUCHED -> Junction_104

Bookmark: Correction auto-intersection des S
Junction_104
    -> GeometryValidator
    -> FeatureJoiner_6 [LEFT]
GeometryValidator
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]FME_CONTROLLER_QUERY_FILE]transformers/dependencies/geometryvalidator/SELF_INTERSECTING.fme
    SUMMARY = Detailed
    PASSED -> FeatureJoiner_6 [RIGHT]
    REPAIRED -> FeatureJoiner_6 [RIGHT]
FeatureJoiner_6
    ATTR_CONFLICT_RES = Use Left
    GEOMETRY_HANDLING = Use Right
    JOIN_KEYS = IDENT_PAR IDENT_PAR AUTO
    JOIN_MODE = Inner
    JOINED -> FeatureHolder_19
    UNJOINED_LEFT -> FeatureHolder_19
FeatureHolder_19
    -> Junction_23

Bookmark: Correction sens lignes
Note: _IDObjetTemp
Counter_3
    CNT_ATTR = _IDObjetTemp
    DOMAIN = IDObjetTemp
    SCOPE = Global
    START = 0
    -> Tester_8
    -> Junction_31
    -> Tester_41
Note: FORME=L
Tester_41
    BOOL_OP = OR
    COMPOSITE_TEST = 1
    TEST_CLAUSE = TEST @Value(FORME) = L
    TEST_MODE = TEST
    PASSED -> linéaires
Note: vers récup info
Junction_31
    -> Junction_28
Note: DELIM~DP~PAR~-
Tester_8
    BOOL_OP = OR
    COMPOSITE_TEST = 1
    TEST_CLAUSE = TEST @Value(autocad_layer) = DELIM~DP~PAR~-
    TEST_MODE = TEST
    PASSED -> DELIM_DP_PAR_-_2

Bookmark: Nettoyage des linéaires
linéaires: FeatureHolder
    -> Tester_121
Note: Exclusion des lignes non concernées
Tester_121
    BOOL_OP = OR
    COMPOSITE_TEST = 1
    TEST_CLAUSE = TEST @Value(autocad_layer) = DELIM~DP~LIM~DEC
    TEST_MODE = TEST
    FAILED -> LengthCalculator
LengthCalculator
    DIM = 2
    LEN_ATTR = _length
    MULT = 1
    -> Tester_36
Note: length=0?
Tester_36
    BOOL_OP = OR
    COMPOSITE_TEST = 1
    TEST_CLAUSE = TEST @Value(_length) = 0
    TEST_MODE = TEST
    FAILED -> GeometryCoercer_7
Note: Forcer les objets en lignes
GeometryCoercer_7
    GQUERY:
      for $geom in //geometry
      where $geom/count(parent::geometry) = 0
      return number($geom/@fme_id)
    KIND = fme_line
    COERCED -> AttributeCreator_149
    UNTOUCHED -> AttributeCreator_149

Bookmark: Récup objet originaux
Note: depuis entrée
Junction_28
    -> FeatureJoiner_9 [RIGHT]
FeatureJoiner_9
    ATTR_CONFLICT_RES = Use Left
    GEOMETRY_HANDLING = Use Left
    JOIN_KEYS = _IDObjetTemp _IDObjetTemp AUTO
    JOIN_MODE = Inner
    JOINED -> FeatureHolder_2
    UNJOINED_RIGHT -> FeatureHolder_2
FeatureHolder_2
    -> Junction_29

Bookmark: Detection DP~PAR dans mauvaise direction
DELIM_DP_PAR_-_2: FeatureHolder
    -> Tester_10

Bookmark: Test polygon?
Tester_10
    BOOL_OP = OR
    COMPOSITE_TEST = 1
    TEST_CLAUSE = TEST @Value(autocad_entity) = autocad_polygon
    TEST_MODE = TEST
    PASSED -> OrientationExtractor

Bookmark: Test orientation + correction des right_hand_rule
Note: left_hand_rule-> sens correct / right_hand_rule-> mauvais sens
OrientationExtractor
    ORIENTATION = _orientation
    -> TestFilter_2
TestFilter_2
    DEFAULT_VALUE = <UNFILTERED>
    TEST_LIST = "BOOL_OP,OR,COMPOSITE_TEST,""""""1"""""",TEST_CLAUSE,TEST @Value(_orientation) = left_hand_rule",left_hand_rule,"BOOL_OP,OR,COMPOSITE_TEST,""""""1"""""",TEST_CLAUSE,TEST @Value(_orientation) = right_hand_rule",right_hand_rule
    left_hand_rule -> FeatureHolder_8
    right_hand_rule -> Orientor_2
Orientor_2
    FLIP_APPEARANCES_CHOICE = Yes
    KIND = REVERSE
    ORIENTED -> OrientationExtractor_2
OrientationExtractor_2
    ORIENTATION = _orientation
    -> FeatureHolder_8
FeatureHolder_8
    -> DELIM_DP_PAR_-
    -> FeatureJoiner_9 [LEFT]

Bookmark: Test sens des linéaires
DELIM_DP_PAR_-: FeatureHolder
    -> GeometryCoercer_5
GeometryCoercer_5
    GQUERY:
      for $geom in //geometry
      where $geom/count(parent::geometry) = 0
      return number($geom/@fme_id)
    KIND = fme_line
    COERCED -> AttributeCreator_149
Note: Sens_ligne
AttributeCreator_149
    ATTR_TABLE = SET_TO Sens_ligne = FME_CONDITIONAL:DEFAULT_VALUE'Objet_a_gauche'BOOL_OP;OR;COMPOSITE_TEST;1;TEST @Value(autocad_layer) = DELIM~DP~PAR~-'Objet_a_droite'FME_NUM_CONDITIONS2___
    -> LineOnLineOverlayer_5 [LINE]
    -> FeatureJoiner_11 [LEFT]
Note: Linéaire défectueux: / -superposé avec DELIM~DP~PAR / -suivant la règle d'objet à gauche / -dans le même sens que le DELIM~DP~PAR~-
Tester_9
    BOOL_OP = COMPOSITE
    COMPOSITE_TEST = 1 AND 2 AND 3
    TEST_CLAUSE:
      TEST @Value(_overlap_autocad_layer) = DELIM~DP~PAR~-
      TEST @Value(Sens_ligne) = Objet_a_gauche
      TEST @Value(_overlap_direction) = same
    TEST_MODE = TEST
    PASSED -> FeatureJoiner_10 [LEFT]
    FAILED -> Tester_43
FeatureJoiner_11
    ATTR_CONFLICT_RES = Use Left
    GEOMETRY_HANDLING = Use Left
    JOIN_KEYS = _IDObjetTemp _IDObjetTemp AUTO
    JOIN_MODE = Inner
    JOINED -> Sampler_7
Sampler_7
    GROUP_BY = _IDObjetTemp
    RATE = 1
    SAMPLE_MODE = No
    SAMPLE_TYPE_LONG = First N Features
    SAMPLED -> Orientor
Orientor
    FLIP_APPEARANCES_CHOICE = Yes
    KIND = REVERSE
    ORIENTED -> FeatureJoiner_9 [LEFT]

Bookmark: Relation lignes superposées
LineOnLineOverlayer_5
    ATTRS_ACCUM_MODE = Use Attributes From One Feature
    CLEANING_TOLERANCE = Automatic
    DEAGGREGATE_INPUT = Yes
    GENERATE_LIST_DROP = YES
    LIST_NAME = _overlaps
    OV_ATTR = _overlaps
    SEPARATE_COLLINEAR_SEGMENTS = Yes
    LINE -> Tester_37
Note: _overlaps{0}._IDObjetTemp à une valeur? / ->Non -> pas de relation constituée
Tester_37
    BOOL_OP = OR
    COMPOSITE_TEST = 1
    TEST_CLAUSE = TEST _overlaps{0}._IDObjetTemp ATTRIBUTE_HAS_A_VALUE ""
    TEST_MODE = TEST
    PASSED -> ListExploder_8
ListExploder_8
    ATTR_ACCUM_MODE = Prefix List Attributes
    INCOMING_PREFIX = _overlap_
    INDEX_ATTR = _element_index
    LIST_ATTR = _overlaps{}
    ELEMENTS -> AttributeRemover_6
Note: _overlap_direction
AttributeRemover_6
    REMOVE_ATTRS = _overlap_autocad_block_name,_overlap_TYPE,_overlaps,_overlap_fme_feature_type,_overlap_ALT,_overlap_autocad_elevation,_overlap_autocad_xscale,_overlap_FORME,_overlap_autocad_rotation,_overlap_MAT,_overlap_autocad_yscale,_overlap_autocad_entity
    -> Tester_9

Bookmark: Si les linéaires déféctueux sont bons avec un autre PAR -> pas de changement de sens
Note: Linéaire similaire bon: / -superposé avec DELIM~DP~PAR / -suivant la règle d'objet à gauche / -dans le sens inverse du DELIM~DP~PAR~-
Tester_43
    BOOL_OP = COMPOSITE
    COMPOSITE_TEST = 1 AND 2 AND 3
    TEST_CLAUSE:
      TEST @Value(_overlap_autocad_layer) = DELIM~DP~PAR~-
      TEST @Value(Sens_ligne) = Objet_a_gauche
      TEST @Value(_overlap_direction) = opposite
    TEST_MODE = TEST
    PASSED -> FeatureJoiner_10 [RIGHT]
Note: stop linéaire si équivalent bon
FeatureJoiner_10
    ATTR_CONFLICT_RES = Use Left
    GEOMETRY_HANDLING = Use Left
    JOIN_KEYS = _IDObjetTemp _IDObjetTemp AUTO
    JOIN_MODE = Inner
    UNJOINED_LEFT -> FeatureJoiner_11 [RIGHT]

Bookmark: Correction du sens des polygones fermés selon logique left hand
Junction_29
    -> Tester_242
Note: entity=polygon?
Tester_242
    BOOL_OP = OR
    COMPOSITE_TEST = 1
    TEST_CLAUSE = TEST @Value(autocad_entity) = autocad_polygon
    TEST_MODE = TEST
    PASSED -> Tester_259
    FAILED -> Junction_30
Note: exclusion objets non concernés
Tester_259
    BOOL_OP = OR
    COMPOSITE_TEST = 1 OR 2
    TEST_CLAUSE:
      TEST @Value(autocad_layer) = INFRA~ROU~AXE~-
      TEST @Value(autocad_layer) = DELIM~DP~PAR~-
    TEST_MODE = TEST
    PASSED -> Junction_30
    FAILED -> GeometryCoercer
Note: vers suite
Junction_30
    -> AttributeCreator_29

Bookmark: Test polygo et anti-polygo
Note: forcer en polygone
GeometryCoercer
    GQUERY:
      for $geom in //geometry
      where $geom/count(parent::geometry) = 0
      return number($geom/@fme_id)
    KIND = fme_polygon
    COERCED -> Counter_10
Note: _ID_test_superpo
Counter_10
    CNT_ATTR = _ID_test_superpo
    DOMAIN = ID_test_superpo
    SCOPE = Global
    START = 0
    -> AttributeRemover_3
AttributeRemover_3
    REMOVE_ATTRS = _overlap_Sens_ligne,_overlap_autocad_zscale,_overlap__IDObjetTemp,_overlap__filename,_overlap_fme_feature_type_original,_overlap_SSCLASSE,_overlap_autocad_source_filename,_overlap_direction,_overlap_CLASSE,_overlap_SSTHEME,_overlap__length,_overlap_autocad_yscale_2,_overlap_autocad_xscale_2,_overlap_autocad_layer,_overlap_THEME,_overlap__orientation
    -> SpatialRelator [Supplier]
    -> SpatialRelator [Requestor]
    -> FeatureJoiner_12 [LEFT]
Note: Requestor dans Supplier
SpatialRelator
    AGGREGATE_HANDLING = Yes
    CALC_CARD = No
    CURVE_BOUNDARY_RULE_PARAM = Default Rule
    LIST_ATTRS_TO_INCLUDE = _ID_test_superpo autocad_layer
    LIST_NAME = _superpo
    PREDICATES = WITHIN
    SUCCESS_ATTR = _related_candidates
    -> Tester_42
Note: info_type_polygone=anti_poly
AttributeCreator_31
    ATTR_TABLE = SET_TO info_type_polygone = anti_poly
    -> AttributeKeeper_18
AttributeKeeper_18
    KEEP_ATTRS = info_type_polygone,_ID_test_superpo
    -> FeatureJoiner_12 [RIGHT]
FeatureJoiner_12
    ATTR_CONFLICT_RES = Use Left
    GEOMETRY_HANDLING = Use Left
    JOIN_KEYS = _ID_test_superpo _ID_test_superpo AUTO
    JOIN_MODE = Inner
    JOINED -> Junction_33
    UNJOINED_LEFT -> Junction_33
Junction_33
    -> TestFilter_5
TestFilter_5
    DEFAULT_VALUE = polygone
    TEST_LIST = "BOOL_OP,OR,COMPOSITE_TEST,""""""1"""""",TEST_CLAUSE,TEST @Value(info_type_polygone) = anti_poly",anti_poly
    anti_poly -> Orientor_5
    polygone -> Orientor_4

Bookmark: Filtre
Note: _related_candidates>=1
Tester_42
    BOOL_OP = OR
    COMPOSITE_TEST = 1
    TEST_CLAUSE = TEST @Value(_related_candidates) >= 1
    TEST_MODE = TEST
    PASSED -> ListExploder
ListExploder
    ATTR_ACCUM_MODE = Prefix List Attributes
    INCOMING_PREFIX = _test_superpo
    INDEX_ATTR = _element_index
    LIST_ATTR = _superpo{}
    ELEMENTS -> Tester_44
Note: STOP relation avec lui même
Tester_44
    BOOL_OP = OR
    COMPOSITE_TEST = 1
    TEST_CLAUSE = TEST @Value(_ID_test_superpo) = @Value(_test_superpo_ID_test_superpo)
    TEST_MODE = TEST
    FAILED -> Tester_45
Note: filtre calques de même type
Tester_45
    BOOL_OP = OR
    COMPOSITE_TEST = 1
    TEST_CLAUSE = TEST @Value(autocad_layer) = @Value(_test_superpoautocad_layer)
    TEST_MODE = TEST
    PASSED -> AttributeCreator_31

Bookmark: Application orientation
Note: right_hand
Orientor_5
    KIND = RIGHT_HAND_RULE
    ORIENTED -> Junction_34
    <REJECTED> -> Junction_34
Note: left_hand
Orientor_4
    KIND = LEFT_HAND_RULE
    ORIENTED -> Junction_34
    <REJECTED> -> Junction_34
Junction_34
    -> Junction_30

Bookmark: Round scales
AttributeCreator_29
    ATTR_TABLE:
      SET_TO xscale_round = @Value(autocad_xscale)
      SET_TO yscale_round = @Value(autocad_yscale)
      SET_TO zscale_round = @Value(autocad_zscale)
    -> AttributeRounder_9
AttributeRounder_9
    PLACES = 3
    ROUND_TYPE = Nearest
    SRC_ATTRS = yscale_round zscale_round xscale_round
    -> Tester_30

Bookmark: Vérif. scales pour recréation
Note: Filtre objets sans scales (1,1,1)
Tester_30
    BOOL_OP = AND
    COMPOSITE_TEST = 1 AND 2 AND 3
    TEST_CLAUSE:
      TEST @Value(autocad_xscale) = 1
      TEST @Value(autocad_yscale) = 1
      TEST @Value(autocad_zscale) = 1
    TEST_MODE = TEST
    PASSED -> FeatureHolder_7
    FAILED -> Tester_29
Note: Diff dans les scales approx (round)?
Tester_29
    BOOL_OP = OR
    COMPOSITE_TEST = 1
    TEST_CLAUSE = TEST @Value(xscale_round) != @Value(yscale_round)
    TEST_MODE = TEST
    PASSED -> FeatureHolder_7
    FAILED -> Tester_11
Note: Diff dans les scales exactes?
Tester_11
    BOOL_OP = OR
    COMPOSITE_TEST = 1 OR 2 OR 3
    TEST_CLAUSE:
      TEST @Value(autocad_xscale) != @Value(autocad_yscale)
      TEST @Value(autocad_yscale) != @Value(autocad_zscale)
      TEST @Value(autocad_xscale) != @Value(autocad_zscale)
    TEST_MODE = TEST
    PASSED -> AttributeCreator_30
    FAILED -> FeatureHolder_7
Note: Normalisation des dim. sur xscale
AttributeCreator_30
    ATTR_TABLE:
      SET_TO autocad_yscale = @Value(autocad_xscale)
      SET_TO autocad_zscale = @Value(autocad_xscale)
    -> FeatureHolder_7
FeatureHolder_7
    -> RESEAU~SLT~BOUCLE~FEU (writer ACAD_4)

Bookmark: Objets Ponctuels
Note: TP pas sur Ponctuel

FME custom transformer FeatureCounter
This transformer counts the number of features passing through, and applies that number as an attribute onto each feature.
It differs from the Counter in that it gives the total count to each feature. It doesn't give each feature a unique, incremented number.
It differs from the StatisticsCalculator in that it does not need an attribute to be selected for analysis.
An optional group-by parameter allows features to be counted in groups.
Transformer Category: Calculated Values
Blocker Transformer: Yes

Parameters:
- FeatureCounterNewAttrParameter = _numfeatures   # New Attribute Name
- GROUP_BY =   # " " Group By

Input (input)
    -> AttributeCreator_2
Note: Create temporary attribute for StatisticsCalculator
AttributeCreator_2
    ATTR_TABLE = SET_TO FeatureCounter_tempattr = 1
    -> StatisticsCalculator
Note: Calculate number of features
StatisticsCalculator
    COMPUTE_HISTOGRAM = NO
    COUNT_ATTR = FeatureCounter_tempattr_count
    GROUP_BY = $(GROUP_BY)
    PREPEND_ATTR_NAME_CHOICE = For multiple results only
    STATS_ATTRS = FeatureCounter_tempattr
    COMPLETE -> AttributeCreator
Note: Create new attribute
AttributeCreator
    ATTR_TABLE = SET_TO $(FeatureCounterNewAttrParameter) = @Value(FeatureCounter_tempattr_count)
    -> AttributeExposer
Note: Expose new attribute
AttributeExposer
    ATTR_LIST = $(FeatureCounterNewAttrParameter)
    -> Output (output)
Note: Output features keeping only new attribute
Output (output)
