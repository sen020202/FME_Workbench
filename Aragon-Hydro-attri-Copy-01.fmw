FME workspace Aragon-Hydro-attri-Copy-01.fmw

Parameters:
- DestDataset_DGNV8 =
- DestDataset_DGNV8_3 =
- FEATURE_TYPES =
- FEATURE_TYPES_2 =
- Hexagon_Hydro_Lines =
- SourceDataset_ESRISHAPE_3 =

Readers:
- ESRISHAPE_1: ESRISHAPE from $(Hexagon_Hydro_Lines)
- ESRISHAPE_2: ESRISHAPE from $(SourceDataset_ESRISHAPE_3)

Writers:
- DGNV8_1: DGNV8 to $(DestDataset_DGNV8)
- DGNV8_2: DGNV8 to $(DestDataset_DGNV8_3)

Hydro-518 (reader ESRISHAPE_1)
    attributes: OBJECTID long, SITUACION char(5), CUENCA char(10), CLASIF char(5), CANALIZ char(5), ESTADO char(5), COMPONEN1D char(5), SUBCUENCA char(250), ID_HOJA char(5), NOMBRE char(250), NIVEL char(5), ID_Fenomen char(5), REGIMEN char(5), TIPO char(5), SHAPE_Leng double
    -> AttributeCreator_2
AttributeCreator_2
    ATTR_TABLE = SET_TO idgs_level_name = Input_Hydro_Lines
    -> LineCombiner
LineCombiner
    ACCUM_ATTRS_NAME = Use Attributes From One Feature
    BREAK = no
    CONNECT_Z_MODE = First Wins
    CONSIDER_NODE_ELEVATION = no
    DEAGGREGATE_GEOMETRY = Deaggregate
    DIRECTION_NAME = direction
    JUNCTIONS_IGNORE_ATTRIBUTES = No
    LINES_AS_SEGMENTS = No
    PRESERVE = no
    TOPOLOGY = End noded
    LINE -> Level1 (writer DGNV8_2)
Level1 (writer DGNV8_2)
Hidro_Teruel_Referance_518 (reader ESRISHAPE_2)
    attributes: id long, d_muni_ine char(50), tipo char(50), nivel_vert char(50), strahler double, cuenca char(50), subcuenca char(50), nombre_cat char(100), shape_leng double, nombre char(150), objectid double, id_masa double, inspire_id char(254), id_demarc char(254), fuente char(254), fecha_alta char(10), c_muni_ine long, fecha_baja char(200)
    -> AttributeCreator
AttributeCreator
    ATTR_TABLE:
      SET_TO idgs_level_name = @Value(nombre)
      SET_TO idgs_color = 6
    -> DGNStyler
DGNStyler
    COLOR_BY_LEVEL_DISPLAY = No
    COLOR_CHOICE_DISPLAY = RGB
    LINE_STYLE = 0
    LINE_WEIGHT = 3
    RGB_COLOR = 1,0.666667,0
    DGNStyled -> Hidro_Teruel_Referance_518 (writer DGNV8_1)
Hidro_Teruel_Referance_518 (writer DGNV8_1)
    attributes: id integer, d_muni_ine char(50), tipo char(50), nivel_vert char(50), strahler double, cuenca char(50), subcuenca char(50), nombre_cat char(100), shape_leng double, nombre char(150), objectid double, id_masa double, inspire_id char(254), id_demarc char(254), fuente char(254), fecha_alta char(10), c_muni_ine integer, fecha_baja char(200)
