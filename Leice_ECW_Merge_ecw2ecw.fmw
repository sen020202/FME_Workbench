FME workspace Leice_ECW_Merge_ecw2ecw.fmw

Parameters:
- SourceDataset_ECW = ""$(FME_MF_DIR)Input\2023_56000_438000_RGB_hr.ecw" "$(FME_MF_DIR)Input\2023_56000_438750_RGB_hr.ecw" "$(FME_MF_DIR)Input\2023_56000_439500_RGB_hr.ecw" "$(FME_MF_DIR)Input\2023_56000_440250_RGB_hr.ecw" "$(FME_MF_DIR)Input\2023_56000_441000_RGB_hr.ecw" "$(FME_MF_DIR)Input\2023_56000_441750_RGB_hr.ecw" "$(FME_MF_DIR)Input\2023_56000_442500_RGB_hr.ecw" "$(FME_MF_DIR)Input\2023_56000_443250_RGB_hr.ecw""   # Source ER Mapper ECW File(s)
- FEATURE_TYPES = ECW
- DestDataset_ECW = $(FME_MF_DIR)output   # Destination ER Mapper ECW Folder

Readers:
- ECW_1: ECW from $(SourceDataset_ECW)

Writers:
- ECW_2: ECW to $(DestDataset_ECW)

ECW (reader ECW_1)
    -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> ECW (writer ECW_2)
ECW (writer ECW_2)
