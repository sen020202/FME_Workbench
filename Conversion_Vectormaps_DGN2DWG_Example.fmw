FME workspace Conversion_Vectormaps_DGN2DWG_Example.fmw

Parameters:
- SourceDataset_DGNV8 = $(FME_MF_DIR)01_Indata\Ekero_Rural.dgn   # Source Bentley MicroStation Design File(s)
- DestDataset_ACAD = $(FME_MF_DIR)04_Export\VectorMap_Export2.dwg   # Destination Autodesk AutoCAD DWG/DXF File
- FEATURE_TYPES =

Readers:
- DGNV8_1: DGNV8 from $(SourceDataset_DGNV8)

Writers:
- ACAD_1: ACAD to $(DestDataset_ACAD)

RO_CYCLEWAY_ASPH_TUNNEL (reader DGNV8_1)
    -> Counter
Counter
    CNT_ATTR = _ID
    DOMAIN = counter
    SCOPE = Global
    START = 1
    -> FeatureMerger [REQUESTOR]
    -> DatabaseJoiner
Note: Workspace for conversion of vectormaps
DatabaseJoiner
    ADDED_FIELDS = Category "Customer Code" Description "Hexagon Internal Code" Included "Object type" Symbol
    ATTR_ACCUM_MODE = Merge Joined
    ATTR_CONFLICT_RES = Use Original
    DATASET = $(FME_MF_DIR_ENCODED)03_ExcelCodelist\Ekero-Feature table for Vector mapping (1).xlsx
    FORMAT = XLSXR
    JOIN_KEYS = igds_level_name "Hexagon Internal Code"
    MATCH_MULTIPLE_DISPLAY = Create a feature for each match
    MATCH_RULE_DISPLAY = Match All (1:M)
    TABLE = Sheet1
    XLSXR_ALLOW_DOLLAR_SIGNS = YES
    XLSXR_CASE_SENSITIVE_FEATURE_TYPES = YES
    XLSXR_CONFIGURATION_DATASET = $(FME_MF_DIR)03_ExcelCodelist\Ekero-Feature table for Vector mapping (1).xlsx
    XLSXR_CREATE_FEATURE_TABLES_FROM_DATA = Yes
    XLSXR_EXPAND_MERGED_CELLS = Yes
    XLSXR_EXPOSED_ATTRS = xlsx_row_id,number(11,0)
    XLSXR_KEEP_SCHEMA_SETTINGS = YES
    XLSXR_READ_BLANK_AS = Missing
    XLSXR_SCAN_SCHEMA_IF_DYNAMIC = No
    XLSXR_SCHEMA = Sheet1,0,Description,char,36,,,1,"Object type",char,9,,,2,Category,char,15,,,3,Symbol,char,7,,,4,"Hexagon Internal Code",char,29,,,5,"Customer Code",char,34,,,6,Included,char,2,,,7,H,string,,,,8,I,string,,,,9,J,string,,,,10,K,string,,,,11,L,string,,,,12,M,string,,,,13,N,string,,,,14,O,string,,,,15,P,string,,,,16,Q,string,,,,17,R,string,,,,18,S,string,,,,19,T,string,,,,20,U,string,,,,21,V,string,,,,22,W,string,,,,23,X,string,,,,24,Y,string,,,,25,Z,string,,,,26,AA,string,,,,27,AB,string,,,,28,AC,string,,,,29,AD,string,,,,30,AE,string,,,,31,AF,string,,,,32,AG,string,,,,33,AH,string,,,,34,AI,string,,,,35,AJ,string,,,,36,AK,string,,,,37,AL,string,,,,38,AM,string,,,,39,AN,string,,,,40,AO,string,,,,41,AP,string,,,,42,AQ,string,,,,43,AR,string,,,,44,AS,string,,,,45,AT,string,,,,46,AU,string,,,,47,AV,string,,,,48,AW,string,,,,49,AX,string,,,,50,AY,string,,,,51,AZ,string,,,,52,BA,string,,,,1,,,,NO,NO,1,"$(FME_MF_DIR_ENCODED)03_ExcelCodelist\Ekero-Feature table for Vector mapping (1).xlsx","0,0,52,150",,NO,NO
    XLSXR_STRIP_SHEETNAME_SPACES = YES
    XLSXR_TABLELIST = Sheet1
    XLSXR_USE_SCHEMA_OTHER_FILES = No
    JOINED -> FeatureMerger [SUPPLIER]
FeatureMerger
    ATTR_ACCUM_MODE = Merge Supplier
    ATTR_CONFLICT_RES = Use Requestor
    IGNORE_NULLS = No
    JOIN_KEYS = @Value(_ID) @Value(_ID) AUTO
    MERGE_TYPE = Attributes Only
    PROCESS_DUPS = No
    REJECT_NULL_MISSING_KEYS = No
    SUPPLIERS_FIRST = No
    MERGED -> GeometryFilter
    NOT_MERGED -> AttributeManager_3
AttributeManager_3
    -> AttributeCreator
AttributeManager_2
    ATTR_TABLE:
      REMOVE fme_feature_type
      REMOVE _ID
      REMOVE Category
      REMOVE Object type
      REMOVE _matched_records
      REMOVE fme_text_string
      REMOVE fme_rotation
      REMOVE fme_text_size
      REMOVE Hexagon Internal Code
    -> Stairs (writer ACAD_1)
Stairs (writer ACAD_1)
    attributes: igds_level_name char(80)

Bookmark: Split_According to geometry
GeometryFilter
    BREAK_AGG = No
    GEOM_PORT_NAMES = Point Line Area Text
    POINT -> Tester_3
    LINE -> Tester_2
    AREA -> Tester_5
    TEXT -> Tester_6
    <UNFILTERED> -> AttributeCreator

Bookmark: Check Point features
Tester_3
    BOOL_OP = OR
    COMPOSITE_TEST = 1
    TEST_CLAUSE = TEST @Value(Object type) = Symbol
    TEST_MODE = TEST
    PASSED -> AttributeManager
    FAILED -> Tester_4
AttributeManager
    -> DWGStyler
Tester_4
    BOOL_OP = OR
    COMPOSITE_TEST = 1
    TEST_CLAUSE = TEST @Value(Object type) = Symbol Rotated
    TEST_MODE = TEST
    PASSED -> DWGStyler
    FAILED -> AttributeCreator
DWGStyler
    BLOCK_NAME = @Value(Symbol)
    BLOCK_ROT = 0
    BLOCK_SIZETYPE_DISPLAY = Scale Factor
    BLOCK_SIZEX = 1.0
    BLOCK_SIZEY = 1.0
    BLOCK_SIZEZ = 1.0
    COLOR = 1,1,0
    TEMPLATE_FILE = $(FME_MF_DIR)02_Templates\Template_Block.dwg
    DWGStyled -> AttributeManager_2

Bookmark: Check Line features
Tester_2
    BOOL_OP = OR
    TEST_CLAUSE = TEST @Value(Object type) = Polyline
    TEST_MODE = TEST
    PASSED -> AttributeManager_2
    FAILED -> AttributeCreator

Bookmark: Check Area features
Tester_5
    BOOL_OP = OR
    TEST_CLAUSE = TEST @Value(Object type) = Polyline
    TEST_MODE = TEST
    PASSED -> AttributeManager_2
    FAILED -> AttributeCreator

Bookmark: Check Text features
Tester_6
    BOOL_OP = OR
    TEST_CLAUSE = TEST @Value(Object type) = Text
    TEST_MODE = TEST
    PASSED -> AttributeManager_2
    FAILED -> AttributeCreator

Bookmark: Misc_Error_Features
AttributeCreator
    ATTR_TABLE = SET_TO Customer Code = Error_@Value(igds_level_name)
    -> AttributeManager_2
