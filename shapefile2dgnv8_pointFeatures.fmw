FME workspace shapefile2dgnv8_pointFeatures.fmw

Parameters:
- SourceDataset_SHAPEFILE = D:\02_Pilot\Vienna subway\Delivery\vsen delivery\UG\SHP\UG_point.shp   # Source Esri Shapefile(s)
- FEATURE_TYPES = UG_point
- DestDataset_DGNV8 = D:\02_Pilot\Vienna subway\Delivery\vsen delivery\UG\POINTS.dgn   # Destination Bentley MicroStation Design File

Readers:
- SHAPEFILE_1: SHAPEFILE from $(SourceDataset_SHAPEFILE)

Writers:
- DGNV8_1: DGNV8 to $(DestDataset_DGNV8)

strasse_point (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> strasse_point (writer DGNV8_1)
strasse_point (writer DGNV8_1)
    attributes: THEMATIK char(200), RTRTYP integer, ANGLE integer, DETAILS char(20), BETREIBER char(200), MATERIAL char(200), ANZAHL double, PROFTYP char(200), DIM_L double, DIM_H double, DIM_BEZ char(200), L_QUAL double, HOEHE1 char(200), H_QUAL1 double, H_BEZ1 char(200), HOEHE2 char(200), H_QUAL2 double, H_BEZ2 char(200)
