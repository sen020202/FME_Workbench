FME workspace shapefile2shapefile.fmw

Parameters:
- SourceDataset_SHAPEFILE = ""D:\2024 Meixner\2024 Vienna Linnen Subway\Vienna_Subway_20240917\ContinuousAutomaticTrain_L.shp" "D:\2024 Meixner\2024 Vienna Linnen Subway\Vienna_Subway_20240917\CableDuct_L.shp" "D:\2024 Meixner\2024 Vienna Linnen Subway\Vienna_Subway_20240917\Cable_L.shp" "D:\2024 Meixner\2024 Vienna Linnen Subway\Vienna_Subway_20240917\BrownCable_L.shp" "D:\2024 Meixner\2024 Vienna Linnen Subway\Vienna_Subway_20240917\BluePipe_L.shp" "D:\2024 Meixner\2024 Vienna Linnen Subway\Vienna_Subway_20240917\BlueCable_L.shp" "D:\2024 Meixner\2024 Vienna Linnen Subway\Vienna_Subway_20240917\BlackPipe_L.shp" "D:\2024 Meixner\2024 Vienna Linnen Subway\Vienna_Subway_20240917\BlackCable_L.shp" "D:\2024 Meixner\2024 Vienna Linnen Subway\Vienna_Subway_20240917\YellowCable_L.shp" "D:\2024 Meixner\2024 Vienna Linnen Subway\Vienna_Subway_20240917\Yellow_power_rail_L.shp" "D:\2024 Meixner\2024 Vienna Linnen Subway\Vienna_Subway_20240917\WhitePipe_L.shp" "D:\2024 Meixner\2024 Vienna Linnen Subway\Vienna_Subway_20240917\WhiteCable_L.shp" "D:\2024 Meixner\2024 Vienna Linnen Subway\Vienna_Subway_20240917\VentilationSystem_P.shp" "D:\2024 Meixner\2024 Vienna Linnen Subway\Vienna_Subway_20240917\Switches_P.shp" "D:\2024 Meixner\2024 Vienna Linnen Subway\Vienna_Subway_20240917\RedPipe_L.shp" "D:\2024 Meixner\2024 Vienna Linnen Subway\Vienna_Subway_20240917\Plugs_P.shp" "D:\2024 Meixner\2024 Vienna Linnen Subway\Vienna_Subway_20240917\Pipe_L.shp" "D:\2024 Meixner\2024 Vienna Linnen Subway\Vienna_Subway_20240917\Pillar_P.shp" "D:\2024 Meixner\2024 Vienna Linnen Subway\Vienna_Subway_20240917\Lights_P.shp" "D:\2024 Meixner\2024 Vienna Linnen Subway\Vienna_Subway_20240917\GreenCable_L.shp" "D:\2024 Meixner\2024 Vienna Linnen Subway\Vienna_Subway_20240917\GrayPipe_L.shp" "D:\2024 Meixner\2024 Vienna Linnen Subway\Vienna_Subway_20240917\GrayCable_L.shp" "D:\2024 Meixner\2024 Vienna Linnen Subway\Vienna_Subway_20240917\EmergencyStationsPlugs_P.shp" "D:\2024 Meixner\2024 Vienna Linnen Subway\Vienna_Subway_20240917\Emergency_Station_P.shp" "D:\2024 Meixner\2024 Vienna Linnen Subway\Vienna_Subway_20240917\Drainage_L.shp" "D:\2024 Meixner\2024 Vienna Linnen Subway\Vienna_Subway_20240917\Doors_P.shp" "D:\2024 Meixner\2024 Vienna Linnen Subway\Vienna_Subway_20240917\Distribution_boxesPlugs_P.shp" "D:\2024 Meixner\2024 Vienna Linnen Subway\Vienna_Subway_20240917\Distribution_boxes_P.shp""   # Source Esri Shapefile(s)
- DestDataset_SHAPEFILE_4 = D:\2024 Meixner\2024 Vienna Linnen Subway\Vienna_Subway_20240917\SHP_WienLinien\Linie\05   # Destination Esri Shapefile Folder
- DestDataset_SHAPEFILE = D:\2024 Meixner\2024 Vienna Linnen Subway\Vienna_Subway_20240917\SHP_WienLinien\Punkt\06   # Destination Esri Shapefile Folder

Readers:
- SHAPEFILE_1: SHAPEFILE from $(SourceDataset_SHAPEFILE)

Writers:
- SHAPEFILE_2: SHAPEFILE to $(DestDataset_SHAPEFILE)
- SHAPEFILE_3: SHAPEFILE to $(DestDataset_SHAPEFILE_4)

ContinuousAutomaticTrain_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
Distribution_boxesPlugs_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
EmergencyStationsPlugs_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
BlackCable_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
BlackPipe_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
BlueCable_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
BluePipe_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
BrownCable_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
Cable_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
CableDuct_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
Distribution_boxes_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
Doors_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
Drainage_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
Emergency_Station_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
GrayCable_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
GrayPipe_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
GreenCable_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
Lights_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
Pillar_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
Pipe_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
Plugs_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
RedPipe_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
Switches_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
VentilationSystem_P (reader SHAPEFILE_1)
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
    -> FeatureHolder
WhiteCable_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
WhitePipe_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
Yellow_power_rail_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
YellowCable_L (reader SHAPEFILE_1)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
    -> FeatureHolder
FeatureHolder
    -> GeometryFilter
GeometryFilter
    FILTER_MODE = SIMPLE
    FILTER_MULTI = FILTER_TYPES]"Point Curve"]FME_CONTROLLER_QUERY_FILE]]FME_CONTROLLER_CHOICE]Simple
    <UNFILTERED> -> GeometryFilter__Unfiltered_
    Point -> AttributeFilter
    Point -> GeometryFilter_Point
    Curve -> AttributeFilter_2
    Curve -> GeometryFilter_Line
GeometryFilter_Point: Inspector
GeometryFilter_Line: Inspector
AttributeFilter
    ATTR_NAME = RTRTYP
    ATTR_VALUES = <Empty>,<Missing>,<Null>,<Unfiltered>,1,2,3,4,5,6,7,8,0
    <EMPTY> -> AttributeFilter__Empty_
    <MISSING> -> AttributeFilter__Missing_
    <NULL> -> AttributeFilter__Null_
    <UNFILTERED> -> AttributeFilter__Unfiltered_
    1 -> AttributeFilter_1
    1 -> AttributeCreator_2
    2 -> AttributeFilter_3
    3 -> AttributeFilter_4
    3 -> AttributeCreator_3
    4 -> AttributeFilter_5
    4 -> AttributeCreator_4
    5 -> AttributeFilter_6
    6 -> AttributeFilter_7
    6 -> AttributeCreator_5
    6 -> AttributeValueMapper
    7 -> AttributeFilter_8
    8 -> AttributeFilter_9
AttributeValueMapper
    DEFAULT_VALUE = 0
    LUT = METAL,200,PLASTIC,300,GLASS,300,CONCRETE,100
    MAPPING_DIRECTION = FORWARD
    SRC = MATERIAL
    VAL_ATTR = MATERIAL
    -> AttributeValueMapper_2
AttributeValueMapper_2
    DEFAULT_VALUE = 0
    LUT = CIRCLE,1,RECTANGLE,2
    MAPPING_DIRECTION = FORWARD
    SRC = PROFTYP
    VAL_ATTR = PROFTYP
    -> AttributeValueMapper_3
AttributeValueMapper_3
    DEFAULT_VALUE = 0
    LUT = EXTERIOR,2,exterior,2,INTERIOR,1,interior,1
    MAPPING_DIRECTION = FORWARD
    SRC = DIM_BEZ
    VAL_ATTR = DIM_BEZ
    -> AttributeValueMapper_4
AttributeValueMapper_4
    DEFAULT_VALUE = 0
    LUT = 5,1,10,2
    MAPPING_DIRECTION = FORWARD
    SRC = L_QUAL
    VAL_ATTR = L_QUAL
    -> AttributeValueMapper_5
AttributeValueMapper_5
    DEFAULT_VALUE = 0
    LUT = 5,1,10,2
    MAPPING_DIRECTION = FORWARD
    SRC = H_QUAL1
    VAL_ATTR = H_QUAL1
    -> AttributeValueMapper_6
AttributeValueMapper_6
    DEFAULT_VALUE = 0
    LUT = 5,1,10,2
    MAPPING_DIRECTION = FORWARD
    SRC = H_QUAL2
    VAL_ATTR = H_QUAL2
    -> AttributeValueMapper_7
AttributeValueMapper_7
    DEFAULT_VALUE = 0
    LUT = Sohle,2,Oberkante,4
    MAPPING_DIRECTION = FORWARD
    SRC = H_BEZ1
    VAL_ATTR = H_BEZ1
    -> AttributeValueMapper_8
AttributeValueMapper_8
    DEFAULT_VALUE = 0
    LUT = Sohle,2,Oberkante,4
    MAPPING_DIRECTION = FORWARD
    SRC = H_BEZ2
    VAL_ATTR = H_BEZ2
    -> 6 (writer SHAPEFILE_2)
6 (writer SHAPEFILE_2) [off]
    attributes: THEMATIK varchar(200), RTRTYP long, ANGLE long, DETAILS varchar(20), BETREIBER varchar(200), MATERIAL varchar(200), ANZAHL number(11,0), PROFTYP varchar(200), DIM_L number(11,0), DIM_H number(11,0), DIM_BEZ varchar(200), L_QUAL number(11,0), HOEHE1 varchar(200), H_QUAL1 number(11,0), H_BEZ1 varchar(200), HOEHE2 varchar(200), H_QUAL2 number(11,0), H_BEZ2 varchar(200)
AttributeFilter__Empty_: Inspector
AttributeFilter__Missing_: Inspector
AttributeFilter__Null_: Inspector
AttributeFilter__Unfiltered_: Inspector
AttributeFilter_1: Inspector
AttributeCreator_2
    ATTR_TABLE = SET_TO THEMATIK = Übergabepunkte
AttributeFilter_3: Inspector
AttributeFilter_4: Inspector
AttributeFilter_5: Inspector
AttributeCreator_3
    ATTR_TABLE = SET_TO THEMATIK = Kontrollschächte
AttributeFilter_6: Inspector
AttributeFilter_7: Inspector
AttributeCreator_4
    ATTR_TABLE = SET_TO THEMATIK = Verteilerkästen
AttributeFilter_8: Inspector
AttributeFilter_9: Inspector
AttributeCreator_5
    ATTR_TABLE = SET_TO THEMATIK = Trägerstrukturen
GeometryFilter__Unfiltered_: Inspector
AttributeFilter_2
    ATTR_NAME = RTRTYP
    ATTR_VALUES = <Empty>,<Missing>,<Null>,<Unfiltered>,1,2,3,4,5,6,7,8,0
    <EMPTY> -> AttributeFilter_2__Empty_
    <MISSING> -> AttributeFilter_2__Missing_
    <NULL> -> AttributeFilter_2__Null_
    <UNFILTERED> -> AttributeFilter_2__Unfiltered_
    <UNFILTERED> -> AttributeCreator_6
    1 -> AttributeFilter_2_1
    2 -> AttributeFilter_2_2
    2 -> AttributeCreator_7
    3 -> AttributeFilter_2_3
    4 -> AttributeFilter_2_4
    5 -> AttributeFilter_2_5
    5 -> AttributeCreator_8
    5 -> AttributeValueMapper_9
    6 -> AttributeFilter_2_6
    7 -> AttributeFilter_2_7
    8 -> AttributeFilter_2_8
AttributeFilter_2__Empty_: Inspector
AttributeFilter_2__Missing_: Inspector
AttributeFilter_2__Null_: Inspector
AttributeFilter_2__Unfiltered_: Inspector
AttributeCreator_6
    ATTR_TABLE = SET_TO THEMATIK = Nicht zutreffend
AttributeFilter_2_1: Inspector
AttributeValueMapper_9
    DEFAULT_VALUE = 0
    LUT = METAL,200,PLASTIC,300,GLASS,300,CONCRETE,100
    MAPPING_DIRECTION = FORWARD
    SRC = MATERIAL
    VAL_ATTR = MATERIAL
    -> AttributeValueMapper_10
AttributeValueMapper_10
    DEFAULT_VALUE = 0
    LUT = CIRCLE,1,RECTANGLE,2
    MAPPING_DIRECTION = FORWARD
    SRC = PROFTYP
    VAL_ATTR = PROFTYP
    -> AttributeValueMapper_11
AttributeValueMapper_11
    DEFAULT_VALUE = 0
    LUT = EXTERIOR,2,exterior,2,INTERIOR,1,interior,1
    MAPPING_DIRECTION = FORWARD
    SRC = DIM_BEZ
    VAL_ATTR = DIM_BEZ
    -> AttributeValueMapper_12
AttributeValueMapper_12
    DEFAULT_VALUE = 0
    LUT = 5,1,10,2
    MAPPING_DIRECTION = FORWARD
    SRC = L_QUAL
    VAL_ATTR = L_QUAL
    -> AttributeValueMapper_13
AttributeValueMapper_13
    DEFAULT_VALUE = 0
    LUT = 5,1,10,2
    MAPPING_DIRECTION = FORWARD
    SRC = H_QUAL1
    VAL_ATTR = H_QUAL1
    -> AttributeValueMapper_14
AttributeValueMapper_14
    DEFAULT_VALUE = 0
    LUT = 5,1,10,2
    MAPPING_DIRECTION = FORWARD
    SRC = H_QUAL2
    VAL_ATTR = H_QUAL2
    -> AttributeValueMapper_15
AttributeValueMapper_15
    DEFAULT_VALUE = 0
    LUT = Sohle,2,Oberkante,4
    MAPPING_DIRECTION = FORWARD
    SRC = H_BEZ1
    VAL_ATTR = H_BEZ1
    -> AttributeValueMapper_16
AttributeValueMapper_16
    DEFAULT_VALUE = 0
    LUT = Sohle,2,Oberkante,4
    MAPPING_DIRECTION = FORWARD
    SRC = H_BEZ2
    VAL_ATTR = H_BEZ2
    -> 5 (writer SHAPEFILE_3)
5 (writer SHAPEFILE_3)
    attributes: THEMATIK varchar(50), RTRTYP long, ANGLE long, DETAILS varchar(20), BETREIBER varchar(50), MATERIAL varchar(50), ANZAHL long, PROFTYP varchar(50), DIM_L number(11,0), DIM_H number(11,0), DIM_BEZ varchar(50), L_QUAL number(11,0), HOEHE1 double, H_QUAL1 number(11,0), H_BEZ1 varchar(50), HOEHE2 double, H_QUAL2 number(11,0), H_BEZ2 varchar(50)
AttributeFilter_2_2: Inspector
AttributeCreator_7
    ATTR_TABLE = SET_TO THEMATIK = Leerrohre/Rohre
AttributeFilter_2_3: Inspector
AttributeFilter_2_4: Inspector
AttributeFilter_2_5: Inspector
AttributeCreator_8
    ATTR_TABLE = SET_TO THEMATIK = Glasfaserkabel
AttributeFilter_2_6: Inspector
AttributeFilter_2_7: Inspector
AttributeFilter_2_8: Inspector
AttributeCreator
    ATTR_TABLE = SET_TO THEMATIK = Nicht zutreffend
