FME workspace dgnv8_shapefile_dgnv82none.fmw

Parameters:
- SourceDataset_DGNV8 = H:\Exchange\JEGO\Height-Test\492\Merged_492_GC.dgn   # Source Bentley MicroStation Design File(s)
- FEATURE_TYPES = REF_04003_Hedge_Ln REF_04003_Retaining_wall_Ln REF_04003_Wall_Ln REF_04003_Wire_fence_Ln REF_04008_Element_Construct_Curb_Use_Ln
- FEATURE_TYPES_3 = CubiertaTer_pol EdiPobCons_lin EdiPobCons_pol
- SourceDataset_SHAPEFILE = ""H:\Exchange\JEGO\Height-Test\492\HEX_DATA\CubiertaTer_pol.shp" "H:\Exchange\JEGO\Height-Test\492\HEX_DATA\EdiPobCons_lin.shp" "H:\Exchange\JEGO\Height-Test\492\HEX_DATA\EdiPobCons_pol.shp""   # Source Esri Shapefile(s)
- SourceDataset_DGNV8_2 = H:\Exchange\JEGO\Height-Test\492\2.dgn   # Source Bentley MicroStation Design File(s)
- FEATURE_TYPES_2 = Junction_4_Output

Readers:
- DGNV8_1: DGNV8 from $(SourceDataset_DGNV8)
- SHAPEFILE_1: SHAPEFILE from $(SourceDataset_SHAPEFILE)
- DGNV8_3: DGNV8 from $(SourceDataset_DGNV8_2)

Junction_4_Output (reader DGNV8_3)
    -> Counter_6
Counter_6
    CNT_ATTR = _count_Point
    DOMAIN = counter
    SCOPE = Global
    START = 1
    -> PointOnLineOverlayer [POINT]
REF_04003_Retaining_wall_Ln (reader DGNV8_1)
    -> Tester_10
Tester_10
    BOOL_OP = OR
    TEST_CLAUSE:
      TEST @Value(igds_level_name) = REF_04003_Retaining_wall_Ln
      TEST @Value(igds_level_name) = REF_04003_Hedge_Ln
      TEST @Value(fme_feature_type) = REF_04003_Wall_Ln
      TEST @Value(igds_level_name) = REF_04003_Wire_fence_Ln
      TEST @Value(igds_level_name) = REF_04008_Element_Construct_Curb_Use_Ln
    TEST_MODE = TEST
    PASSED -> CoordinateRounder
CoordinateRounder
    XPREC = 7
    YPREC = 7
    ZPREC = 7
    ROUNDED -> Counter_4
Counter_4
    CNT_ATTR = _count
    DOMAIN = counter
    SCOPE = Global
    START = 1
    -> GeometryFilter_2
GeometryFilter_2
    BREAK_AGG = No
    GEOM_PORT_NAMES = Line Area
    LINE -> GeometryCoercer
    AREA -> GeometryCoercer
GeometryCoercer
    GQUERY:
      for $geom in //geometry
      where $geom/count(parent::geometry) = 0
      return number($geom/@fme_id)
    KIND = fme_line
    COERCED -> LineOnAreaOverlayer [LINE]
    COERCED -> Tester_12
Tester_12
    BOOL_OP = OR
    TEST_CLAUSE = TEST @Value(igds_level_name) = REF_04003_Wire_fence_Ln
    TEST_MODE = TEST
    PASSED -> Offsetter_4
    FAILED -> Offsetter_5
Offsetter_4
    MODE = Cartesian Coordinate
    XOFF = 0
    YOFF = 0
    ZOFF = -0.3
    OFFSET -> VertexExtractor
Offsetter_5
    MODE = Cartesian Coordinate
    XOFF = 0
    YOFF = 0
    ZOFF = -0.5
    OFFSET -> VertexExtractor
VertexExtractor
    Point -> Counter_3
    Point -> PointOnAreaOverlayer [POINT]
Counter_3
    CNT_ATTR = _count_Vertex_ID
    DOMAIN = counter
    SCOPE = Global
    START = 1
    -> Bufferer
Bufferer
    ANGLE = 22.5
    CAP_STYLE = Arc
    CORNER_STYLE = Arc
    MODE = AREA
    OFFSET = 0.0001
    OFFSET_UNITS = NONE
    PRECISION = APPROX
    BUFFERED -> SpatialFilter [Filter]
492-cuuberter-pol (reader SHAPEFILE_1)
    attributes: OBJECTID long, ID_Fenomen varchar(5), ID_HOJA varchar(5), NOMBRE varchar(254), TIPO varchar(5), FIGURA varchar(5), CODIGO varchar(9), SHAPE_Leng double, SHAPE_Area double
    -> Counter
Counter
    CNT_ATTR = _count_POLY
    DOMAIN = counter
    SCOPE = Global
    START = 1
    -> TestFilter_2
TestFilter_2
    DEFAULT_VALUE = <UNFILTERED>
    PASSED_TEST_GROUP_OUTPUT = FIRST
    TEST_LIST:
      "BOOL_OP,OR,COMPOSITE_TEST,""""""1 OR 2 OR 3 OR 4 OR 5"""""",TEST_CLAUSE,TEST @Value(TIPO) = VAL
      TEST @Value(TIPO) = CER
      TEST @Value(TIPO) = MCO
      TEST @Value(TIPO) = MUR
      TEST @Value(TIPO) = PUE",@Value(TIPO) = VAL
    <UNFILTERED> -> LineOnAreaOverlayer [AREA]
LineOnAreaOverlayer
    CLEANING_TOLERANCE = 0.00001
    DEAGGREGATE_INPUT = Yes
    OV_ATTR = _overlaps
    AREA -> Tester
Tester
    BOOL_OP = OR
    TEST_CLAUSE = TEST @Value(_overlaps) = 0
    TEST_MODE = TEST
    PASSED -> PointOnAreaOverlayer [AREA]
    FAILED -> Counter_2
PointOnAreaOverlayer
    DEAGGREGATE_INPUT = Yes
    OV_ATTR = _overlaps
    POLYS_FIRST = NO
    AREA -> Tester_2
Tester_2
    BOOL_OP = OR
    TEST_CLAUSE = TEST @Value(_overlaps) = 0
    TEST_MODE = TEST
    FAILED -> Counter_2
Counter_2
    CNT_ATTR = _count_ID
    DOMAIN = counter
    SCOPE = Global
    START = 1
    -> DonutHoleExtractor
DonutHoleExtractor
    DEAGGREGATE_INPUT = Yes
    OUTERSHELL -> Junction_2
    HOLE -> Junction_2
    HOLE -> Clipper [CLIPPER]
Junction_2
    -> Counter_5
Counter_5
    CNT_ATTR = _count_IND_POLY_ID
    DOMAIN = counter
    SCOPE = Global
    START = 1
    -> GeometryCoercer_2
GeometryCoercer_2
    GQUERY:
      for $geom in //geometry
      where $geom/count(parent::geometry) = 0
      return number($geom/@fme_id)
    KIND = fme_line
    COERCED -> VertexExtractor_2
    COERCED -> PointOnLineOverlayer [LINE]
VertexExtractor_2
    Point -> SpatialFilter [Candidate]
SpatialFilter
    AGGREGATE_HANDLING = Yes
    ATTR_ACCUM_MODE = Prefix Filter
    ATTR_PREFIX = _MM_
    BASE_TYPE = Multiple Filters
    CURVE_BOUNDARY_RULE_PARAM = Default Rule
    PASS_CRITERIA = Pass Against One Filter
    PREDATTR = _predicate
    PREDICATES = CONTAINS
    USE_BOUNDING_BOX = No
    PASSED -> StatisticsCalculator
    FAILED -> Junction
StatisticsCalculator
    CALCULATION_MODE = NUMERIC
    FEAT_STATS = _MM__z,NUMERIC_MODE,MIN,MAX,COUNT,,,,,,,,,,
    GROUP_BY = _MM__count_Vertex_ID
    SUMMARY -> FeatureJoiner [RIGHT]
    COMPLETE -> FeatureJoiner [LEFT]
FeatureJoiner
    ATTR_CONFLICT_RES = Prefer Left
    GEOMETRY_HANDLING = Prefer Left
    JOIN_KEYS = _MM__count_Vertex_ID _MM__count_Vertex_ID AUTO
    JOIN_MODE = Inner
    JOINED -> AttributeManager
AttributeManager
    ATTR_TABLE = SET_TO _z = @Value(_MM__z.min)
    -> Junction
Junction
    -> Sorter_2
Sorter_2
    GROUP_BY = _count_ID
    SORT_PARM = _vertex_number NATURAL ASCENDING
    SORTED -> LineBuilder_2
LineBuilder_2
    ACCUM_INPUT_ATTRS = Use Attributes From One Feature
    GROUP_BY = _count_IND_POLY_ID
    REMOVE_DUPLICATES = No
    LINE -> GeometryCoercer_3
    POLYGON -> GeometryCoercer_3
GeometryCoercer_3
    GQUERY:
      for $geom in //geometry
      where $geom/count(parent::geometry) = 0
      return number($geom/@fme_id)
    KIND = fme_polygon
    COERCED -> Clipper [CANDIDATE]
Clipper
    BOUNDARY_CASES = INSIDE
    CLEANING_TOLERANCE = Automatic
    CLIPPED_ATTR = _clipped
    CLIPPERS_FIRST = NO
    GENERATE_LIST = NO
    GROUP_BY = _count_ID
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
PointOnLineOverlayer
    DEAGGREGATE_INPUT = Yes
    MEASURE_TYPE = Continuous
    MERGE_MEASURES = Yes
    OV_ATTR = _overlaps
    TOLERANCE = 0.01
    POINT -> Counter_8
    LINE -> Tester_3
Counter_8
    CNT_ATTR = _count_Point_ID
    DOMAIN = counter
    SCOPE = Global
    START = 1
    -> Tester_4
Tester_4
    BOOL_OP = OR
    TEST_CLAUSE = TEST @Value(_overlaps) = 0
    TEST_MODE = TEST
    FAILED -> Bufferer_2
Bufferer_2
    ANGLE = 22.5
    CAP_STYLE = Arc
    CORNER_STYLE = Arc
    MODE = AREA
    OFFSET = 0.001
    OFFSET_UNITS = NONE
    PRECISION = APPROX
    BUFFERED -> SpatialFilter_2 [Filter]
Tester_3
    BOOL_OP = OR
    TEST_CLAUSE = TEST @Value(_overlaps) = 0
    TEST_MODE = TEST
    PASSED -> AreaBuilder
    FAILED -> Counter_9
Counter_9
    CNT_ATTR = _count_Line_IDD
    DOMAIN = counter
    SCOPE = Global
    START = 1
    -> VertexExtractor_3
VertexExtractor_3
    Point -> Counter_7
Counter_7
    CNT_ATTR = _count_Vertex_ID
    DOMAIN = counter
    SCOPE = Global
    START = 1
    -> SpatialFilter_2 [Candidate]
SpatialFilter_2
    AGGREGATE_HANDLING = Yes
    ATTR_ACCUM_MODE = Prefix Filter
    ATTR_PREFIX = _PA_
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> StatisticsCalculator_2
    FAILED -> LineBuilder
    FAILED -> Sorter
StatisticsCalculator_2
    CALCULATION_MODE = NUMERIC
    FEAT_STATS = _PA__count_Point_ID,NUMERIC_MODE,MIN,MAX,COUNT,,,,,,,,,,
    GROUP_BY = _PA__count_Point_ID
    SUMMARY -> FeatureJoiner_2 [RIGHT]
    COMPLETE -> FeatureJoiner_2 [LEFT]
FeatureJoiner_2
    ATTR_CONFLICT_RES = Prefer Left
    GEOMETRY_HANDLING = Prefer Left
    JOIN_KEYS = _PA__count_Point_ID _PA__count_Point_ID AUTO
    JOIN_MODE = Inner
    JOINED -> VertexCreator
VertexCreator
    MEASURE_TYPE = Continuous
    MODE_NAME = Replace with Point
    XVAL = @Value(_x)
    YVAL = @Value(_y)
    ZVAL = @Value(_PA__count_Point_ID.min)
    -> LineBuilder
    -> Sorter
LineBuilder
    ACCUM_INPUT_ATTRS = Use Attributes From One Feature
    GROUP_BY = _count_Line_IDD
    REMOVE_DUPLICATES = No
    LINE -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    GROUP_BY = _count_IND_POLY_ID
    LINES_AS_SEGMENTS = No
    POLY_ACCUM_ATTRS_NAME = Use Attributes From One Feature
    SNAPTYPE_PARAM = None
Sorter
    GROUP_BY = _count_Line_IDD

FME custom transformer 3DAnchoredSnapper
Purpose
Snap vertex from lines or polygones in 3D. It is equivalent to the Vertex snapping mode of the snapper.
Usage
Input Ports :
Candidate : This transformer accepts lines and polygons in 3d.
Anchor : This transformer accepts lines and polygons in 3d.
Output Ports :
Snapped : Objects from Candidate port, snapped (measures lost).
Not_Snapped : Objects from Candidate port, not snapped.
Degenerate : Objects from Candidate port, snapped to a different geometry type (ie polygon to line or line to point).
Requirements
FME 2019.0
Published Parameters
dist : snapping distance
FME_PROCESS_GROUP_BY : group by
Limitation
This transformer does not clean the data (just delete duplicate coordinates) and measures are lost.

Parameters:
- DIST = @Value(dist)   # Snapping distance
- FME_PROCESS_GROUP_BY =   # "" Group By

Candidate (input)
    -> DimensionExtractor
Junction_3
    -> Degenerate (output)
Anchor (input)
    -> DimensionExtractor_2
FeatureMerger
    ATTR_ACCUM_MODE = Merge Supplier
    ATTR_CONFLICT_RES = Use Requestor
    GROUP_BY = $(FME_PROCESS_GROUP_BY)
    IGNORE_NULLS = No
    JOIN_KEYS = 1 1 AUTO
    MERGE_TYPE = Attributes Only
    PROCESS_DUPS = NO
    REJECT_NULL_MISSING_KEYS = No
    SUPPLIERS_FIRST = No
    MERGED -> AttributeCreator_2
    UNMERGED_REQUESTOR -> Not_Snapped (output)
    USED_SUPPLIER -> AttributeCreator
    <REJECTED> -> AttributeCreator
AttributeCreator_2
    ATTR_TABLE = SET_TO _status = snapped
    -> ParameterFetcher
AttributeCreator
    ATTR_TABLE = SET_TO _status = ref
    -> ParameterFetcher
Note: ref first
Sorter
    SORT_PARM = _status ALPHA ASCENDING
    SORTED -> PythonCaller_3
PythonCaller_3
    NEW_ATTRIBUTES = snapped error
    PYTHONSOURCE:
      import fme
      import fmeobjects
      import numpy as np

      #take two numpy arrays, calculate the distances and switch candidates coordinates to reference one when within distance
      #nodestosnap : numpy array to be updated
      #nodesref :  numpy array of reference
      #dist : maximum snapping distance

      #calculate the eucledian distance between two points
      #pointA : numpy array (1,3)
      #pointB : numpy array (1,3)
      def distancePoints(pointA,pointB):
          dp = np.linalg.norm(pointA - pointB, ord=2)
          return dp

      #calculate the eucledian distance between two arrays
      #arrayA : numpy array (n,3)
      #arrayB : numpy array (n,3)
      def distanceArrays(arrayA,arrayB):
          nbPtsA = arrayA.shape[0]
          nbPtsB = arrayB.shape[0]
          dm = np.empty((nbPtsA, nbPtsB), dtype=np.double)
          for i in range(0, nbPtsA):
              for j in range(0, nbPtsB):
                  dm[i, j] = distancePoints(arrayA[i], arrayB[j])
          return dm

      #snap points in a numpy array within a distance from reference points in an other array
      #nodestosnap numpy array of points (n,3), coordinates to be snapped
      #nodesref numpy array of points (n,3) of reference
      #dist : snap distance in ground units
      #out:
      #status : True if modified, False if not
      #snapped : numpy array of vertexes (changed or not)
      def snap(nodestosnap, nodesref,dist):
          #calculate a matrix of distances
          matdist = (distanceArrays(nodestosnap, nodesref))
          #gives the index of the closest point in ref
          closest = (np.argmin(matdist, axis=1 ))
          #gives the distance of the closest
          mindist =matdist[np.arange(len(matdist)), closest]
          #filter based on snap distance
          tobechanged = mindist<=dist
          #init status to False, unchanged
          status = False
          #test if any vertex is to be changed
          if np.any(tobechanged):
              #increase size of boolean matrix for comparaison
              tobechanged = np.repeat(tobechanged[:,np.newaxis], 3, 1)
              #change coordinates to closest when within distance
              snapped = np.where(tobechanged,nodesref[closest],nodestosnap)
              status = True
          else:
              snapped = nodestosnap
          return  {'snapped':snapped, 'status':status}


      # Template Class Interface:
      # When using this class, make sure its name is set as the value of
      # the 'Class or Function to Process Features' transformer parameter
      class FeatureProcessor(object):
          def __init__(self):
              #init the reference array
              self.ref=  np.empty([0, 3], dtype=float)

          def input(self,feature):
              #if reference feature, added to ref array
              if feature.getAttribute('_status')=='ref':
                  self.ref = np.append(self.ref,np.array(feature.getAllCoordinates()),axis=0);
              #if candidate, compared to reference, updated and output
              if feature.getAttribute('_status')=='snapped':

                  #candidate array init (could be one line but easier to change if needed)
                  tosnap =  np.empty([0, 3], dtype=float)
                  tosnap = np.append(tosnap,np.array(feature.getAllCoordinates()),axis=0);
                  #snapping (output is an array
                  result = snap(tosnap, self.ref,feature.getAttribute('dist'))
                  snappedArray = result['snapped']
                  snapped = snappedArray.tolist()
                  #add the status (snapped or not)
                  feature.setAttribute("snapped",result['status'])

                  if result['status'] == False:
                      self.pyoutput(feature)
                      print(result['status'])
                  else:
                      #recreate a line (improvement would be to merge with existing to keep measures for unchanged points ?)
                      finalLine =fmeobjects.FMELine([tuple(l) for l in snapped])
                      #validation, could be done in the array
                      finalLine.removeDuplicates(True)
                      #appending after reset allows to keep the traits
                      #test for geometry types and degenerate geom
                      if  feature.getGeometryType()== fmeobjects.FME_GEOM_POLYGON and finalLine.numPoints()>2:
                          finalpolyg = fmeobjects.FMEPolygon(finalLine)
                          finalpolyg.copyNameFromGeometry(feature.getGeometry())
                          finalpolyg.copyTraitsFromGeometry(feature.getGeometry(),True)
                          feature.setGeometry(finalpolyg)
                      elif feature.getGeometryType()== fmeobjects.FME_GEOM_LINE and finalLine.numPoints()>1:
                          finalLine.copyNameFromGeometry(feature.getGeometry())
                          finalLine.copyTraitsFromGeometry(feature.getGeometry(),True)
                          feature.setGeometry(finalLine)
                      else:
                          feature.setGeometry(finalLine)
                          feature.setAttribute("error","degenerate")
                          feature.setGeometry(finalLine)
                      self.pyoutput(feature)


          def close(self):
              pass
    PYTHONSYMBOL = FeatureProcessor
    -> AttributeRemover
AttributeRemover
    REMOVE_ATTRS = _status
    -> TestFilter
TestFilter
    DEFAULT_VALUE = <UNFILTERED>
    TEST_LIST = "BOOL_OP,OR,COMPOSITE_TEST,""""""1"""""",TEST_CLAUSE,TEST @Value(error) = degenerate",Degenerate,"BOOL_OP,OR,COMPOSITE_TEST,""""""1"""""",TEST_CLAUSE,TEST @Value(snapped) = Yes",Snapped,"BOOL_OP,OR,COMPOSITE_TEST,""""""1"""""",TEST_CLAUSE,TEST @Value(snapped) = No",Not snapped
    Degenerate -> Degenerate (output)
    Snapped -> Snapped (output)
    Not snapped -> Not_Snapped (output)
    <UNFILTERED> -> Terminator
Degenerate (output)
Snapped (output)
Not_Snapped (output)
Terminator
    MESSAGE = Unexpected situation.
Unused_Ref (output)

Bookmark: Filter 3d
DimensionExtractor
    DIM_ATTR = _dimension
    -> Tester
Tester
    BOOL_OP = OR
    TEST_CLAUSE = TEST @Value(_dimension) = 3
    TEST_MODE = TEST
    PASSED -> GeometryFilter
    FAILED -> AttributeCreator_5

Bookmark: error messages
AttributeCreator_5
    ATTR_TABLE = SET_TO error = feature not in 3d
    -> Junction_3
AttributeCreator_6
    ATTR_TABLE = SET_TO error = feature geometry not accepted.
    -> Junction_3

Bookmark: Validation
GeometryFilter
    BREAK_AGG = No
    GEOM_PORT_NAMES = Line Area
    LINE -> Junction
    AREA -> Junction
    <UNFILTERED> -> AttributeCreator_6
Junction
    -> FeatureMerger [REQUESTOR]

Bookmark: Filter 3d
DimensionExtractor_2
    DIM_ATTR = _dimension
    -> Tester_2
Tester_2
    BOOL_OP = OR
    TEST_CLAUSE = TEST @Value(_dimension) = 3
    TEST_MODE = TEST
    PASSED -> GeometryFilter_2
    FAILED -> AttributeCreator_3

Bookmark: error messages
AttributeCreator_3
    ATTR_TABLE = SET_TO error = feature not in 3d
    -> Unused_Ref (output)
AttributeCreator_4
    ATTR_TABLE = SET_TO error = feature geometry not accepted.
    -> Unused_Ref (output)

Bookmark: Validation
GeometryFilter_2
    BREAK_AGG = No
    GEOM_PORT_NAMES = Line Area
    LINE -> Junction_2
    AREA -> Junction_2
    <UNFILTERED> -> AttributeCreator_4
Junction_2
    -> FeatureMerger [SUPPLIER]

Bookmark: dist as a number
ParameterFetcher
    ATTR_LIST = dist $(DIST)
    -> ExpressionEvaluator
ExpressionEvaluator
    ACTION = Create New Attribute
    EXPRESSION = @Value(dist)+0.0
    VAL_ATTR = dist
    -> Sorter
