FME workspace geodatabase_file__dgnv8.fmw

Parameters:
- SourceDataset_GEOTIFF = C:\FME_MKGG_Tools\Geylor_peak\DTM\Area02.tif   # Source GeoTIFF File(s)
- FEATURE_TYPES_2 = GEOTIFF
- SourceDataset_XLSXR = C:\FME_MKGG_Tools\Geylor_peak\Name_Dataset.xlsx   # Source Microsoft Excel File(s)
- FEATURE_TYPES_3 = Sheet1
- DestDataset_DGNV8 = C:\FME_MKGG_Tools\Geylor_peak\PILOT\Same_as_GDB_Rough.dgn   # Destination Bentley MicroStation Design File
- SourceDataset_GEODATABASE_FILE = C:\FME_MKGG_Tools\Geylor_peak\PILOT\PilotBase_V02_sectors_1A_B\PilotBase_V02_sectors_1A_B.gdb   # File Geodatabase
- FEATURE_TYPES = ADDRESS ADDRESSEDENTRANCE ADRSTREETSEGMENT ADRSUBUNIT ADRUNIT ADVERTISEMENTSIGN AIRCONDITIONINGUNIT AIRPORTAREA AIRPORTTERMINAL AMENITYLIGHTINGCOLUMN ANTENNA ANTENNASURFACE ANTENNATOPPOINT AREACLASSIFICATION ATMSHELTER BARBECUEAREA BEACH BLDHIGHESTPOINT BLDMCHIGHESTPOINT BLDMCPLINTH BLDMCREPRESENTATIONPOINT BLDMCROOFLINE BLDMCROOFSURFACE BLDMCSTRUCTHIGHESTPOINT BLDREPRESENTATIONPOINT BLDROOFLINE BLDROOFSURFACE BLDSTRUCTHIGHESTPOINT BOLLARD BOLLARDLINE BREAKLINE BRIDGE BUILDING BUILDINGCOURTYARD BUILDINGMISCCONSTRUCTION BUILDINGOVERHANG BUILDINGPLINTH BUILDINGUNDERGROUNDOUTLINE BUNKERSAND BUOY BUSH BUSLAYBY BUSSTOPPOLE BUSSTOPSHELTER CABLECARLINE CABLECARPYLON CANAL CANALSURFACE CANALWATERCOURSEEDGE CANALWATERCOURSESURFACE CATTLETRAP CEMETERY CHANNEL CHIMNEY CHIMNEYSURFACE CLIFF COASTALFACILITIES COMMUNITY COMMUNITYBOUNDARY COMMUNITYPOINT CONCRETESLAB CONSTRUCTIONSITE CONTOURLINE CULVERT CURBSTONE CURBSTONE1 CUSTOMERCARE CUTANDFILL CYCLE_NETWORK_LINE CYCLE_NETWORK_POLYGON CYCLINGTRACK CYCLINGTRACK1 DAM DECORATIONBUSHES DISTRICT DISTRICTBOUNDARY DISTRICTPOINT DITCH DITCHEDGE DITCHSURFACE DOLPHIN DRIVEWAY DRIVEWAY1 DRIVEWAYS DUCTMARKER EMBANKMENT EMIRATE EMIRATEBOUNDARY EMIRATEPOINT FAIRWAY FENCE FENCETREE FLOODWATERLINE FLOWERBED FLYOVER FOOTBRIDGE FORMLINE FOUNTAIN FOUNTAINSURFACE GASMARKER GASPIPELINEVENT GATE GENERALPOLE GEODETICCONTROL GOLFCOURSE GRAVE GRAVEPOINT GULLYDRAINAGE GULLYSURFACE HEDGE HELLICOPTERLANDINGPAD INTERTIDALZONE IRRIGATIONSURFACE IRRIGATIONSYSTEM JOGGING_TRACKS_LINE JOGGING_TRACKS_POLYGON LAND LANDSCAPE LANDSCAPE1 LETTERBOX LETTERBOXGROUP LIGHTPOLE LINTEL LINTELCURVE LINTELSURFACE MANHOLE MANHOLESURFACE MARINEINSTRUMENT METROFOOTPRINT METROLINEBUILDING METROTRACK MISCCURVE MISCMAST MISCMASTSURFACE MISCMASTTOPPOINT MISCPOINT MISCROADFURNITURECURVE MISCROADFURNITUREPOINT MISCROADFURNITURESURFACE MISCSTREETLIGHTING MISCSTRUCTUREPOINT MISCSTRUCTURESURFACE MISCSURFACE MISCSURFACE1 MISCTELECOMMSURFACE MISCTELECOMMUNICATION MISCWATERSTRUCTURECURVE MISCWATERSTRUCTUREPOINT MISCWATERSTRUCTURESURFACE MUNICIPALITY MUNICIPALITYBOUNDARY MUNICIPALITYPOINT NAMELOCATION NAMEVALIDITYSURFACE NATIONAL NATIONALBOUNDARY NATIONALPOINT OASIS OILWELL ORNAMENTALFEATURE ORNAMENTALFEATURESURFACE ORNAMENTALFEATURETOPPOINT PARK PARKING PARKING1 PARKINGMACHINE PATH PATH1 PEDESTRIANAREA PEDESTRIANAREA1 PERM PIER PILLAR PIPELINE PLANPLOT PLANROADCENTERLINE PLANROADEDGE PLAYGROUND PLOT POWERLINE PROJECTAREA PROJECTSHEETS PUTTINGGREEN PYLON PYLONSURFACE RACETRACK RADAR RAILING RAMP ROADBARRIER ROADCENTRELINE ROADCENTRELINE1 ROADEDGE ROADEDGE1 ROADINTERSECTION ROADINTERSECTION1 ROADISLAND ROADISLAND1 ROADLIGTINGCOLUMN ROADMARKINGAREA ROADMARKINGLINE ROADPOLE ROADSHOULDER ROADSHOULDER1 ROADSIGNPOLE ROADSURFACE ROADSURFACE1 ROADTUNNEL ROCKERY SAFETYBUOYLINE SEAPORT SEARESCUETOWER SEASHORE SEASURFACE SECTOR SERVICECORRIDOR SHELTER SIGN SLOPE SPORTFACILITIES SPOTHEIGHT SPRING STAIRS STREAM STREAMSURFACE STREAMWATERCOURSEEDGE STREAMWATERCOURSESURFACE SWIMMINGPOOL TANKSURFACE TEEINGGROUND TELEPHONEBOOTH TRACK TRACK1 TRACKSURFACE TRAFFICHUMP TRAFFICSIGNALPOLE TRAMTRACK TRAMTRACKFOOTPRINT TREE VASE WADI WADISURFACE WADIWATERCOURSESURFACE WALL WALLMOUNTEDBRACKET WALLSURFACE WASTEBIN WASTEDISPOSALSITE WATERSURFACE WELL WELLSURFACE ZARIBAH ZONE
- DestDataset_GEODATABASE_FILE = C:\FME_MKGG_Tools\Geylor_peak\PILOT\PilotBase_V02_sectors_1A_B\out\1.gdb   # File Geodatabase

Readers:
- GEOTIFF_1: GEOTIFF from $(SourceDataset_GEOTIFF)
- XLSXR_1: XLSXR from $(SourceDataset_XLSXR)
- GEODATABASE_FILE_1: GEODATABASE_FILE from $(SourceDataset_GEODATABASE_FILE)

Writers:
- DGNV8_1: DGNV8 to $(DestDataset_DGNV8)
- GEODATABASE_FILE_2: GEODATABASE_FILE to $(DestDataset_GEODATABASE_FILE)

ADDRESS (reader GEODATABASE_FILE_1)
    attributes: OBJECTID integer, ENGID char(20), POSITIONALACCURACY double, TYPEOFDATASOURCE char(30), PROJECTLIST char(30), SOURCEOFORIGIN char(30), MUNICIPALITYNAME char(5), AD_FGDREPRESENTATION char(30), ADDRESSID integer, ADDRESSNUMBER char(30), STREETNUMBER integer, ADDRESSCODE char(30), SECTORADMID integer, ADDRESSTYPE char(30), LANDSCAPEUSE char(30), PRIMARYUSEENG char(50), PARKINGMACHINETYPE char(30), OWNERSHIPTYPE char(50), PRICODE integer, WELLSURFACEID integer, WASTEBINID integer, MISCSTREETLIGHTINGTYPE char(30), NAMEVALIDITYSURFACEID integer, ROADNUMBER integer, BLDMCREPRESENTATIONPOINTID integer, DITCHID integer, CANALWATERCOURSESURFACEID integer, CASEID char(25), AIRPORTAREAID integer, CUTANDFILLID integer,
      NUMBEROFPARKINGS integer, ROUTE_TYPE char(30), BLDSTRUCTHIGHESTPOINTID integer, AIRCONDITIONINGUNITID integer, PROJECTAREAID integer, MASTTYPE char(30), CORRIDOR10WIDTH double, WADITYPE char(30), SIZEY double, DUCTCATEGORY char(30), FLOWERBEDID integer, PARKINGTYPE char(30), ORNAMENTALTYPE char(30), PLOTDIMENSION char(200), BUSSTOPPOLEID integer, ANTENNATOPPOINTID integer, MISCWATERSURFACETYPE char(30), MISCWATERSTRUCTUREPOINTID integer, CORRIDOR04TYPE char(30), STREAMWATERCOURSESURFACEID integer, IRRIGATIONSURFACEID integer, COMMENTS char(30), ROADID char(50), ROADINTERSECTIONTYPE char(30), CORRIDOR09TYPE char(30), ROADSURFACEID integer, CORRIDOR11WIDTH double, CEMETRYTYPE char(30), NAMEARABIC char(500), CANALWATERCOURSEEDGEID integer,
      GATEID integer, WALLWITHFENCE char(1), WORKTYPE char(25), BOLLARDLINEID integer, CATTLETRAPID integer, CORRIDOR04WIDTH double, ADDRESSEDENTRANCEID integer, WELLID integer, GASPIPELINEVENTID integer, CHIMNEYID integer, SIGNID integer, FOOTBRIDGECLASSIFICATION char(30), ANTENNATYPE char(30), COSTRUCTION_FORECAST_YEAR date, BUILDINGOVERHANGID integer, TERMINALNUMBER integer, BOLLARDTYPE char(30), CORRIDOR07TYPE char(30), CABLECARPYLONID integer, MISCSURFACEID integer, ADRUNITTYPE char(30), SHAPE_Area double, DIMLENGTH char(50), SECTORNUMBERADM char(30), FLOWERBEDCATEGORY char(30), EMIRATEID integer, SWIMMINGPOOLID integer, VASETYPE char(30), EMBANKMENTID integer, COMMPOPNAMEENG char(50),
      SHELTERID integer, ORNAMENTALFEATURESURFACEID integer, PILLARTYPE char(30), HEDGEID integer, NATIONAL char(25), ROADSHOULDERID integer, LBOWNER char(30), WASHEDATHOSPITAL char(500), CONSTRUCTIONSITEID integer, PLOTID char(20), DIAMETER double, TOTAL_LENGTH double, FOUNTAINSURFACEID integer, DATA_SOURCE char(30), DISTRTICTNAMEENG char(500), MISCWATERPOINTTYPE char(30), PHYSICALSTATUS char(30), GRAVENUMBER integer, CONTOURTYPE char(30), BUNKERSANDID integer, NUMBEROFPLANTS integer, ROADTUNNELID integer, TANKSURFACEID integer, TREEID integer, CULVERTTYPE char(30), DISTRICTID char(255), PRIMARYUSAGETYPE char(50), ASSCREENTYPE char(30), LISTMUNICIPALITY char(30), GASMARKERID integer,
      BRIDGEID integer, SHELTERTYPE char(30), IRRIGATIONSYSTEMID integer, ZONEADMID integer, ZONETPSS char(50), MISCSTRUCTUREPOINTID integer, FLAT_ID char(10), MISCSTRUCTURESURFACEID integer, ROADCENTRELINEID integer, NAMERESOLUTION char(30), SIGNALLAMPTYPE char(30), CYCLINGTRACKID integer, GENERALPOLEID integer, FOOTBRIDGEID integer, POWERLINEID integer, BLDMCROOFLINEID integer, MISCTELCOMMSURFACEID integer, ROADCLASS char(30), GRAVEID integer, RACETRACKID integer, AIRPORTAREATYPE char(30), DRIVEWAYTYPE char(30), ROADSURFACETYPE char(30), TRAFFICHUMPTYPE char(30), WASTEDISPOSALSITEID integer, RESERVATIONWIDTH double, NUMBEROFBARBECUE integer, ATMSHELTERID integer, BUOYID integer, BUILDINGMISCINTERNALID integer,
      MISCMASTTOPPOINTID integer, PEDESTRIANAREAACCESS char(30), PIERID integer, CANCELATDATE date, HEDGETYPE char(30), LANDID integer, CORRIDOR01TYPE char(30), ADRSUBUNITID integer, COASTALFACILITIESID integer, SECTORTPSSNUMBER char(100), CORRIDOR03TYPE char(30), CORRIDOR10TYPE char(30), SPORTFACILITIESID integer, OVERHANGTYPE char(30), NATIONALID integer, MUNICIPALITY char(50), CORRIDOR01WIDTH double, STAIRSTYPE char(30), WADISURFACEID integer, SHADING char(30), COMMUNITYNAMEARA char(500), CORRIDOR08WIDTH double, COMNAMECOMPOSITEENG char(255), LINTELTYPE char(30), TRAMTRACKID integer, PLANROADEDGEID char(255), BREAKLINEID integer, ROADLIGTINGCOLUMNID integer, CABLECARTYPE char(30), ISSHELTERED char(1),
      ROADMARKINGAREAID integer, ANTENNAID integer, CORRIDOR06TYPE char(30), BLDREPRESENTATIONPOINTID integer, MISCCURVEID integer, FOUNTAINID integer, FOOTBRIDGETYPE char(30), MISCSTRUCTURESURFACETYPE char(50), CONCRETESLABTYPE char(30), CABLECARLINEID integer, DAMID integer, DISTRICTENG char(255), GISID char(20), COMMUNITYBOUNDARYID integer, MUNICIPALITYBOUNDARYID integer, MAPNAME char(255), CURBSTONEID integer, GULLYDRAINAGEID integer, RAMPID integer, WADIID integer, DUCTTYPE char(30), CONCRETESLABID integer, PLANROADCNID char(255), STAIRSID integer, WADIWATERCOURSESURFACEID integer, MISCRFSURFACE char(30), ID1 double, COMMUNITYNAMEENG char(500), CULVERTID integer, RLCHEIGHT smallint,
      MISCRFCURVE char(30), ROADPOLEID integer, SCID integer, ZONENUMBERADM char(30), COMMPOPNAMEARA char(50), AGE integer, LIGHTING char(30), ROADMARKINGLINETYPE char(30), CORRIDOR09WIDTH double, BLDMCSTRUCTHIGHESTPOINTID integer, BUSSTOPPOLETYPE char(30), HEIGHT double, GENERALPOLETYPE char(30), SECUSEENG char(50), PARKINGID integer, BUILDINGID char(30), MUNICIPALITYID integer, PROJECTSCALE char(30), METROTRACKID integer, OVERRIDE blob, DRIVEWAYID integer, AIRCONDITIONINGUNITTYPE char(30), LETTERBOXID integer, MUNICIPALITYARA char(50), LIGHTPOLETYPE char(30), RADARID integer, AREACLASSIFICATIONSUBTYPE char(50), SIGNTYPES char(30), GRAVEPOINTID integer, CORRIDOR06WIDTH double,
      PLANPLOTID char(255), SECONDARYUSAGETYPE char(50), TELEPHONEBOOTHTYPE char(30), CORRIDOR05WIDTH double, CANALID integer, CATTLETRAPTYPE char(30), EXTENSIONTYPE char(10), TRACKSURFACEID integer, CANCELDATE date, AREACLASSIFICATIONID integer, TREETYPE char(30), WASTEBINTYPE char(30), CORRIDOR05TYPE char(30), CREATEDBY char(30), ADSDI_GUID char(38), ROADBARRIERID integer, CHIMNEYSURFACEID integer, BUILDINGPLINTHID integer, COMNAMECOMPOSITEARA char(255), CANALTYPE char(30), PLAYGROUNDID integer, ROOFLINETYPE char(30), MISCPOINTID integer, ROADBARRIERTYPE char(30), RULEID_1 integer, MISCTELECOMMUNICATIONID integer, CHANNELID integer, MISCSTREETLIGHTINGID integer, NAMEOFTHEDRIVER char(500), ORNAMENTALFEATUREPRIORITY integer,
      INITIATEDBY char(50), BEACHID integer, DISTRICTNAMEENG char(500), BUSLAYBYTYPE char(30), BOLLARDID integer, SHAPE_Length double, PRIMARYUSAGECATEGORYTYPE integer, SPORTSTYPE char(30), DESCRIPTION char(250), CORRIDOR11TYPE char(30), LIGHTPOLEID integer, STRUCTUREPLACEMENTTYPE char(30), FLOODWATERLINEID integer, SEASURFACEID integer, SIZEX double, ISSUEDATE date, CALCULATEDAREA double, CORRIDOR02TYPE char(30), PYLONSURFACEID integer, ROADSHOULDERTYPE char(30), LOCATIONNAMETYPE char(30), ROADMARKINGAREATYPE char(30), MANHOLESURFACEID integer, LANDSCAPETYPE char(30), OVERRIDE_1 blob, DITCHEGDEID integer, SUBUNITIDENTIFIER char(50), ORIGEAST double, IMAGE char(250), WITHLIGHT char(1),
      VASEID integer, OASISID integer, ROADMARKINGLINEID integer, MISCWATERSTRUCTURESURFACEID integer, METROTRACKFOOTPRINTID integer, SPOTHEIGHTID double, DUCTMARKERID integer, BPSKEY char(25), UTILITYCLEARANCEDATE date, RESERVATIONTYPE char(25), CORRIDOR08TYPE char(30), WMBWATTS char(30), EMIRATESNATIONALGRID char(255), SEAPORTID integer, ASNUMBEROFFACES char(30), SURFACE_COLOR char(30), ROADISLANDTYPE char(30), ROOFSURFACETYPE char(30), ADRSTREETSEGMENTID integer, BURIALPERMISSIONNUMBER char(500), LINTELCURVEID integer, NAMEENGLISH char(500), VEHICLEUSED char(500), WATERSURFACEID integer, DIRECTION char(30), TYPEOFSPOTHEIGHT char(30), EXISTING_STATUS char(30), FAIRWAYID integer, LANDSCAPEID integer, BUILDINGMISCCONSTRUCTIONID char(30),
      DISTRICTPOINTID integer, AIRPORTTERMINALID integer, STRUCTUREFORM char(30), CANALSURFACEID integer, POLENUMBER integer, ORGHORREFSYSTEM char(250), PAVEMENTTYPE char(30), BUSSTOPSHELTERID integer, PRIMARYUSEARA char(50), STATUS char(50), ISSUEDDATE char(50), MUNICIPALITYENG char(5), STREAMID integer, FOOTPATHTYPE char(30), DIMBREADTH char(50), DATE_MODIFIED date, NAMELOCATIONID integer, ROADISLANDID integer, ZARIBAHID integer, LBMOUNT char(30), STREETID integer, HELLICOPTERLANDINGPADID integer, IRRIGATIONTYPE char(30), ORNAMENTALFEATUREID integer, BUSHID integer, TEEINGGROUNDID integer, TRAFFICSIGNALPOLEID integer, PATHID integer, GENDER char(30), PLANNINGSTATUS char(50),
      EMIRATEPOINTID integer, FENCETYPE char(30), MANHOLETYPE char(30), MODIFIEDDATE date, CORRIDOR02WIDTH double, MAPNUMBER char(255), ID2 double, APPROVEDBY char(50), PARKID integer, DECORATIONBUSHESID integer, BARRIERTYPE char(30), PMNUMBER char(30), GUID char(38), CURBSTONETYPE char(30), ROADEDGEID integer, PLANNEDAREAIMPERIAL double, ADVERTISEMENTSIGNTYPE char(30), SERVICESTATUS char(50), BLDHIGHESTPOINTID integer, WITHIN_UGB char(30), SEASHORETYPE char(30), FORMLINEID integer, BARBECUEAREAID integer, GOLFCOURSEID integer, MISCWATERSTRUCTURECURVEID integer, POWERLINETYPE char(30), BUSSTOPSHELTERTYPE char(30), SHAPE_AREA00 double, APPROVALLETTER char(50), GATETYPE char(30),
      POINTID char(50), FGDREPRESENTATION char(10), TYPEOFBREAKLINE char(30), WIDTH double, SPRINGID integer, TANKID integer, TEMPORALSTATUS char(25), WMBLENGTH char(30), DEVELOPER char(30), RAILINGTYPE char(30), MISCWATERCURVETYPE char(50), TRAMTRACKFOOTPRINTID integer, DEMOLITIONDATE date, PERMITID integer, CUTFILLTYPE char(30), COMPLETIONDATE date, CORRIDOR07WIDTH double, SECUSEARA char(50), IDENTIFICATION integer, REMARKS char(50), PEDESTRIANAREAID integer, REINFORCEMENTTYPE char(30), AMENITYLIGHTINGCOLUMNID integer, CALCULATEDHEIGHT double, SECTORTPSS char(50), ADRUNITID integer, LETTERBOXGROUPID integer, CYCLE_PARKING_AVAILABILATY char(30), HABITATTYPE char(30), MISCROADFURNITURECURVEID integer,
      REQNUM char(13), COMMUNITYENG char(255), EMIRATES char(25), MANHOLEID integer, CORRIDOR03WIDTH double, DISTRICTNAMEARA char(500), CUSTOMERCAREID integer, PARKINGMACHINEID integer, SETUPDATE char(50), LINTELSURFACEID integer, NATIONALITY char(30), ANTENNASURFACEID integer, DITCHTYPE char(30), BUILDINGNUMBEROFFLOORS integer, PLANNEDAREA char(50), ROADINTERSECTIONID integer, BLDMCPLINTHID integer, MISCSTRUCTUREPOINTTYPE char(30), PROJECTSHEETSID integer, ROADSHOULDERUSAGETYPE char(30), SEARESCUETOWERID integer, SAFETYBUOYLINEID integer, SLOPEGROUNDTYPE char(30), ONWANI_STREET_NAME char(30), DISTRICTBOUNDARYID integer, BUILDINGCOURTYARDID integer, NUMBEROFBUSHES integer, ORGVERREFSYSTEM char(250), NAMEPOPULARENGLISH char(500), PAVEMENT_TYPE char(30),
      FENCEID integer, CHIMNEYTYPE char(30), TELEPHONEBOOTHID integer, RLCWATTS char(30), ZARIBAHTYPE char(30), WALLSURFACEID integer, MISCMASTID integer, MONUMENTPROTECTIONTYPE char(30), ROADTUNNELTYPE char(30), AREACLASSIFICATIONCATEGORY integer, COMMUNITYID char(25), NAMEPOPULARARABIC char(500), PYLONID integer, NATIONALBOUNDARYID integer, MISCROADFURNITUREPOINTID integer, GEODETICCONTROLID integer, PLANNEDAREAMETRIC double, LANDTYPE char(30), POOLTYPE char(30), TRAFFICHUMPID integer, CYCLINGTRACKTYPE char(30), REMARK char(500), SLOPEID integer, TRAFFICSIGNALPOLETYPE char(30), RULEID integer, EMBANKMENTTYPE char(30), LINTELID integer, PILLARID integer, STREAMSURFACEID integer, STREAMWATERCOURSEEDGEID integer,
      NATIONALPOINTID integer, LISTEMIRATE char(30), PIPELINEID integer, MISCTELECOMMUNICATIONTYPE char(30), EMIRATEBOUNDARYID integer, ROADSIGNPOLEID integer, SLOPETYPE char(30), POOLOWNER char(30), BOLLARDMATERIAL char(30), OILWELLID integer, ALCHEIGHT char(30), ROAD_TYPE char(30), AREA_NAME char(30), CEMETRYID integer, BUILDINGINTERNALID integer, MEDIUMTYPE char(30), MISCROADFURNITURESURFACEID integer, MISCRFPOINT char(30), NUMBEROFBULBS char(30), GEODB_OID integer, FENCETREEID integer, DITCHSURFACEID integer, BUSLAYBYID integer, CONTOURLINEID integer, RADARTYPE char(30), SEASHOREID integer, SPORTFACILITYTYPE char(30), MODIFIEDBY char(30), PIPELINETYPE char(30), AREACLASSIFICATIONTYPE integer,
      DOLPHINID integer, SECCODE integer, ADVERTISEMENTSIGNID integer, WALLMOUNTEDBRACKETID integer, ADRSTREETID integer, CREATIONDATE date, RAILINGID integer, WELLTYPE char(30), MUNICIPALITYPOINTID integer, COMMUNITYPOINTID integer, RAMPTYPE char(30), SHELTERUSAGE char(30), BUILDINGUNDERGROUNDOUTLINEID integer, PUTTINGGREENID integer, PLANTING char(30), WASTEDISPOSALSITETYPE char(30), APPROVALCODE char(50), MARINEINSTRUMENTID integer, SIGNALLENSTYPE char(30), ADDRESSPLATETEXT char(50), DISTRICTARA char(50), TRACKID integer, BUOYTYPE char(30), BURIALDATEANDTIME date, POINTTYPE char(50), ROADSIGNTYPE char(50), COMMUNITYARA char(255), ROCKERYID integer, WALLTYPE char(30), GULLYDRAINAGETYPE char(30),
      LBCOLOR char(30), PHOTOURL char(500), RACETRACKUSE char(30), ALCWATTS char(30), BLDMCROOFSURFACEID integer, SHAPE_LEN00 double, ROADTYPE char(30), BLDROOFLINEID integer, DUCTMATERIALTYPE char(30), UPCID char(25), COASTALFCLTYSTRCTRTYPE char(30), ORNAMENTALFEATURETOPPOINTID integer, METROLINEBUILDINGID integer, ORIENTATION double, NAME char(500), INTERTIDALZONEID integer, VASEATTACHMENTTYPE char(30), ORIGNORTH double, ORIGHEIGHT double, COURTYARDTYPE char(30), BLDROOFSURFACEID integer, PLOTNUMBER char(50), TRACKTYPE char(30), WALLID integer, APPROVALDATE date, CURBSTONESTYLE char(30), BRIDGETYPE char(30), STARTDATE date, PROJECTID char(25), WITHCOLOR char(1),
      ELMSKEY char(255), DATE_RECEIVED date, DATEOFDEATH date, MISCMASTSURFACEID integer, UNITIDENTIFIER char(50), POPULATION double, MONUMENTMARKTYPE char(30), WELLUSAGE char(30), BLDMCHIGHESTPOINTID integer
    -> FeatureJoiner [LEFT]
Sheet1 (reader XLSXR_1)
    attributes: Type char(16), Dataset_Name char(23), Geometry_Type char(8)
    -> FeatureJoiner [RIGHT]
FeatureJoiner
    ATTR_CONFLICT_RES = Use Left
    GEOMETRY_HANDLING = Use Left
    JOIN_KEYS = fme_feature_type Dataset_Name AUTO
    JOIN_MODE = Inner
    JOINED -> Level1 (writer DGNV8_1)
    JOINED -> Junction
    UNJOINED_LEFT -> SurfaceDraper [DRAPE_FEATURES]
    <REJECTED> -> StatisticsCalculator
    <REJECTED> -> Junction
StatisticsCalculator
    COMPUTE_HISTOGRAM = NO
    COUNT_ATTR = _count
    GROUP_BY = fme_feature_type
    MAX_ATTR = _max
    MEAN_ATTR = _mean
    MIN_ATTR = _min
    PREPEND_ATTR_NAME_CHOICE = For multiple results only
    STATS_ATTRS = fme_feature_type
    SUM_ATTR = _sum
GEOTIFF (reader GEOTIFF_1)
    -> SurfaceDraper [POINTS/LINES]
SurfaceDraper
    ADDZ_TYPE = Replace Z
    DRAPE_TYPE = VERTEX
    INTERPOLATION_TYPE = AUTO
    TOLERANCE = 0.2
    DRAPED_FEATURES -> Level1 (writer DGNV8_1)
    DRAPED_FEATURES -> Junction
Junction
    -> Tester
    -> FeatureClass1 (writer GEODATABASE_FILE_2)
Tester
    BOOL_OP = OR
    COMPOSITE_TEST = 1
    TEST_CLAUSE = TEST @Value(fme_feature_type) = JOGGING_TRACKS_LINE
    TEST_MODE = TEST
FeatureClass1 (writer GEODATABASE_FILE_2)
Level1 (writer DGNV8_1)
    attributes: OBJECTID integer, ENGID char(20), POSITIONALACCURACY double, TYPEOFDATASOURCE char(30), PROJECTLIST char(30), SOURCEOFORIGIN char(30), MUNICIPALITYNAME char(5), AD_FGDREPRESENTATION char(30), ADDRESSID integer, ADDRESSNUMBER char(30), STREETNUMBER integer, ADDRESSCODE char(30), SECTORADMID integer, ADDRESSTYPE char(30), LANDSCAPEUSE char(30), PRIMARYUSEENG char(50), PARKINGMACHINETYPE char(30), OWNERSHIPTYPE char(50), PRICODE integer, WELLSURFACEID integer, WASTEBINID integer, MISCSTREETLIGHTINGTYPE char(30), NAMEVALIDITYSURFACEID integer, ROADNUMBER integer, BLDMCREPRESENTATIONPOINTID integer, DITCHID integer, CANALWATERCOURSESURFACEID integer, CASEID char(25), AIRPORTAREAID integer, CUTANDFILLID integer,
      NUMBEROFPARKINGS integer, ROUTE_TYPE char(30), BLDSTRUCTHIGHESTPOINTID integer, AIRCONDITIONINGUNITID integer, PROJECTAREAID integer, MASTTYPE char(30), CORRIDOR10WIDTH double, WADITYPE char(30), SIZEY double, DUCTCATEGORY char(30), FLOWERBEDID integer, PARKINGTYPE char(30), ORNAMENTALTYPE char(30), PLOTDIMENSION char(200), BUSSTOPPOLEID integer, ANTENNATOPPOINTID integer, MISCWATERSURFACETYPE char(30), MISCWATERSTRUCTUREPOINTID integer, CORRIDOR04TYPE char(30), STREAMWATERCOURSESURFACEID integer, IRRIGATIONSURFACEID integer, COMMENTS char(30), ROADID char(50), ROADINTERSECTIONTYPE char(30), CORRIDOR09TYPE char(30), ROADSURFACEID integer, CORRIDOR11WIDTH double, CEMETRYTYPE char(30), NAMEARABIC char(500), CANALWATERCOURSEEDGEID integer,
      GATEID integer, WALLWITHFENCE char(1), WORKTYPE char(25), BOLLARDLINEID integer, CATTLETRAPID integer, CORRIDOR04WIDTH double, ADDRESSEDENTRANCEID integer, WELLID integer, GASPIPELINEVENTID integer, CHIMNEYID integer, SIGNID integer, FOOTBRIDGECLASSIFICATION char(30), ANTENNATYPE char(30), COSTRUCTION_FORECAST_YEAR char(14), BUILDINGOVERHANGID integer, TERMINALNUMBER integer, BOLLARDTYPE char(30), CORRIDOR07TYPE char(30), CABLECARPYLONID integer, MISCSURFACEID integer, ADRUNITTYPE char(30), SHAPE_Area double, DIMLENGTH char(50), SECTORNUMBERADM char(30), FLOWERBEDCATEGORY char(30), EMIRATEID integer, SWIMMINGPOOLID integer, VASETYPE char(30), EMBANKMENTID integer, COMMPOPNAMEENG char(50),
      SHELTERID integer, ORNAMENTALFEATURESURFACEID integer, PILLARTYPE char(30), HEDGEID integer, NATIONAL char(25), ROADSHOULDERID integer, LBOWNER char(30), WASHEDATHOSPITAL char(500), CONSTRUCTIONSITEID integer, PLOTID char(20), DIAMETER double, TOTAL_LENGTH double, FOUNTAINSURFACEID integer, DATA_SOURCE char(30), DISTRTICTNAMEENG char(500), MISCWATERPOINTTYPE char(30), PHYSICALSTATUS char(30), GRAVENUMBER integer, CONTOURTYPE char(30), BUNKERSANDID integer, NUMBEROFPLANTS integer, ROADTUNNELID integer, TANKSURFACEID integer, TREEID integer, CULVERTTYPE char(30), DISTRICTID char(255), PRIMARYUSAGETYPE char(50), ASSCREENTYPE char(30), LISTMUNICIPALITY char(30), GASMARKERID integer,
      BRIDGEID integer, SHELTERTYPE char(30), IRRIGATIONSYSTEMID integer, ZONEADMID integer, ZONETPSS char(50), MISCSTRUCTUREPOINTID integer, FLAT_ID char(10), MISCSTRUCTURESURFACEID integer, ROADCENTRELINEID integer, NAMERESOLUTION char(30), SIGNALLAMPTYPE char(30), CYCLINGTRACKID integer, GENERALPOLEID integer, FOOTBRIDGEID integer, POWERLINEID integer, BLDMCROOFLINEID integer, MISCTELCOMMSURFACEID integer, ROADCLASS char(30), GRAVEID integer, RACETRACKID integer, AIRPORTAREATYPE char(30), DRIVEWAYTYPE char(30), ROADSURFACETYPE char(30), TRAFFICHUMPTYPE char(30), WASTEDISPOSALSITEID integer, RESERVATIONWIDTH double, NUMBEROFBARBECUE integer, ATMSHELTERID integer, BUOYID integer, BUILDINGMISCINTERNALID integer,
      MISCMASTTOPPOINTID integer, PEDESTRIANAREAACCESS char(30), PIERID integer, CANCELATDATE char(14), HEDGETYPE char(30), LANDID integer, CORRIDOR01TYPE char(30), ADRSUBUNITID integer, COASTALFACILITIESID integer, SECTORTPSSNUMBER char(100), CORRIDOR03TYPE char(30), CORRIDOR10TYPE char(30), SPORTFACILITIESID integer, OVERHANGTYPE char(30), NATIONALID integer, MUNICIPALITY char(50), CORRIDOR01WIDTH double, STAIRSTYPE char(30), WADISURFACEID integer, SHADING char(30), COMMUNITYNAMEARA char(500), CORRIDOR08WIDTH double, COMNAMECOMPOSITEENG char(255), LINTELTYPE char(30), TRAMTRACKID integer, PLANROADEDGEID char(255), BREAKLINEID integer, ROADLIGTINGCOLUMNID integer, CABLECARTYPE char(30), ISSHELTERED char(1),
      ROADMARKINGAREAID integer, ANTENNAID integer, CORRIDOR06TYPE char(30), BLDREPRESENTATIONPOINTID integer, MISCCURVEID integer, FOUNTAINID integer, FOOTBRIDGETYPE char(30), MISCSTRUCTURESURFACETYPE char(50), CONCRETESLABTYPE char(30), CABLECARLINEID integer, DAMID integer, DISTRICTENG char(255), GISID char(20), COMMUNITYBOUNDARYID integer, MUNICIPALITYBOUNDARYID integer, MAPNAME char(255), CURBSTONEID integer, GULLYDRAINAGEID integer, RAMPID integer, WADIID integer, DUCTTYPE char(30), CONCRETESLABID integer, PLANROADCNID char(255), STAIRSID integer, WADIWATERCOURSESURFACEID integer, MISCRFSURFACE char(30), ID1 double, COMMUNITYNAMEENG char(500), CULVERTID integer, RLCHEIGHT integer,
      MISCRFCURVE char(30), ROADPOLEID integer, SCID integer, ZONENUMBERADM char(30), COMMPOPNAMEARA char(50), AGE integer, LIGHTING char(30), ROADMARKINGLINETYPE char(30), CORRIDOR09WIDTH double, BLDMCSTRUCTHIGHESTPOINTID integer, BUSSTOPPOLETYPE char(30), HEIGHT double, GENERALPOLETYPE char(30), SECUSEENG char(50), PARKINGID integer, BUILDINGID char(30), MUNICIPALITYID integer, PROJECTSCALE char(30), METROTRACKID integer, OVERRIDE string, DRIVEWAYID integer, AIRCONDITIONINGUNITTYPE char(30), LETTERBOXID integer, MUNICIPALITYARA char(50), LIGHTPOLETYPE char(30), RADARID integer, AREACLASSIFICATIONSUBTYPE char(50), SIGNTYPES char(30), GRAVEPOINTID integer, CORRIDOR06WIDTH double,
      PLANPLOTID char(255), SECONDARYUSAGETYPE char(50), TELEPHONEBOOTHTYPE char(30), CORRIDOR05WIDTH double, CANALID integer, CATTLETRAPTYPE char(30), EXTENSIONTYPE char(10), TRACKSURFACEID integer, CANCELDATE char(14), AREACLASSIFICATIONID integer, TREETYPE char(30), WASTEBINTYPE char(30), CORRIDOR05TYPE char(30), CREATEDBY char(30), ADSDI_GUID char(38), ROADBARRIERID integer, CHIMNEYSURFACEID integer, BUILDINGPLINTHID integer, COMNAMECOMPOSITEARA char(255), CANALTYPE char(30), PLAYGROUNDID integer, ROOFLINETYPE char(30), MISCPOINTID integer, ROADBARRIERTYPE char(30), RULEID_1 integer, MISCTELECOMMUNICATIONID integer, CHANNELID integer, MISCSTREETLIGHTINGID integer, NAMEOFTHEDRIVER char(500), ORNAMENTALFEATUREPRIORITY integer,
      INITIATEDBY char(50), BEACHID integer, DISTRICTNAMEENG char(500), BUSLAYBYTYPE char(30), BOLLARDID integer, SHAPE_Length double, PRIMARYUSAGECATEGORYTYPE integer, SPORTSTYPE char(30), DESCRIPTION char(250), CORRIDOR11TYPE char(30), LIGHTPOLEID integer, STRUCTUREPLACEMENTTYPE char(30), FLOODWATERLINEID integer, SEASURFACEID integer, SIZEX double, ISSUEDATE char(14), CALCULATEDAREA double, CORRIDOR02TYPE char(30), PYLONSURFACEID integer, ROADSHOULDERTYPE char(30), LOCATIONNAMETYPE char(30), ROADMARKINGAREATYPE char(30), MANHOLESURFACEID integer, LANDSCAPETYPE char(30), OVERRIDE_1 string, DITCHEGDEID integer, SUBUNITIDENTIFIER char(50), ORIGEAST double, IMAGE char(250), WITHLIGHT char(1),
      VASEID integer, OASISID integer, ROADMARKINGLINEID integer, MISCWATERSTRUCTURESURFACEID integer, METROTRACKFOOTPRINTID integer, SPOTHEIGHTID double, DUCTMARKERID integer, BPSKEY char(25), UTILITYCLEARANCEDATE char(14), RESERVATIONTYPE char(25), CORRIDOR08TYPE char(30), WMBWATTS char(30), EMIRATESNATIONALGRID char(255), SEAPORTID integer, ASNUMBEROFFACES char(30), SURFACE_COLOR char(30), ROADISLANDTYPE char(30), ROOFSURFACETYPE char(30), ADRSTREETSEGMENTID integer, BURIALPERMISSIONNUMBER char(500), LINTELCURVEID integer, NAMEENGLISH char(500), VEHICLEUSED char(500), WATERSURFACEID integer, DIRECTION char(30), TYPEOFSPOTHEIGHT char(30), EXISTING_STATUS char(30), FAIRWAYID integer, LANDSCAPEID integer, BUILDINGMISCCONSTRUCTIONID char(30),
      DISTRICTPOINTID integer, AIRPORTTERMINALID integer, STRUCTUREFORM char(30), CANALSURFACEID integer, POLENUMBER integer, ORGHORREFSYSTEM char(250), PAVEMENTTYPE char(30), BUSSTOPSHELTERID integer, PRIMARYUSEARA char(50), STATUS char(50), ISSUEDDATE char(50), MUNICIPALITYENG char(5), STREAMID integer, FOOTPATHTYPE char(30), DIMBREADTH char(50), DATE_MODIFIED char(14), NAMELOCATIONID integer, ROADISLANDID integer, ZARIBAHID integer, LBMOUNT char(30), STREETID integer, HELLICOPTERLANDINGPADID integer, IRRIGATIONTYPE char(30), ORNAMENTALFEATUREID integer, BUSHID integer, TEEINGGROUNDID integer, TRAFFICSIGNALPOLEID integer, PATHID integer, GENDER char(30), PLANNINGSTATUS char(50),
      EMIRATEPOINTID integer, FENCETYPE char(30), MANHOLETYPE char(30), MODIFIEDDATE char(14), CORRIDOR02WIDTH double, MAPNUMBER char(255), ID2 double, APPROVEDBY char(50), PARKID integer, DECORATIONBUSHESID integer, BARRIERTYPE char(30), PMNUMBER char(30), GUID char(38), CURBSTONETYPE char(30), ROADEDGEID integer, PLANNEDAREAIMPERIAL double, ADVERTISEMENTSIGNTYPE char(30), SERVICESTATUS char(50), BLDHIGHESTPOINTID integer, WITHIN_UGB char(30), SEASHORETYPE char(30), FORMLINEID integer, BARBECUEAREAID integer, GOLFCOURSEID integer, MISCWATERSTRUCTURECURVEID integer, POWERLINETYPE char(30), BUSSTOPSHELTERTYPE char(30), SHAPE_AREA00 double, APPROVALLETTER char(50), GATETYPE char(30),
      POINTID char(50), FGDREPRESENTATION char(10), TYPEOFBREAKLINE char(30), WIDTH double, SPRINGID integer, TANKID integer, TEMPORALSTATUS char(25), WMBLENGTH char(30), DEVELOPER char(30), RAILINGTYPE char(30), MISCWATERCURVETYPE char(50), TRAMTRACKFOOTPRINTID integer, DEMOLITIONDATE char(14), PERMITID integer, CUTFILLTYPE char(30), COMPLETIONDATE char(14), CORRIDOR07WIDTH double, SECUSEARA char(50), IDENTIFICATION integer, REMARKS char(50), PEDESTRIANAREAID integer, REINFORCEMENTTYPE char(30), AMENITYLIGHTINGCOLUMNID integer, CALCULATEDHEIGHT double, SECTORTPSS char(50), ADRUNITID integer, LETTERBOXGROUPID integer, CYCLE_PARKING_AVAILABILATY char(30), HABITATTYPE char(30), MISCROADFURNITURECURVEID integer,
      REQNUM char(13), COMMUNITYENG char(255), EMIRATES char(25), MANHOLEID integer, CORRIDOR03WIDTH double, DISTRICTNAMEARA char(500), CUSTOMERCAREID integer, PARKINGMACHINEID integer, SETUPDATE char(50), LINTELSURFACEID integer, NATIONALITY char(30), ANTENNASURFACEID integer, DITCHTYPE char(30), BUILDINGNUMBEROFFLOORS integer, PLANNEDAREA char(50), ROADINTERSECTIONID integer, BLDMCPLINTHID integer, MISCSTRUCTUREPOINTTYPE char(30), PROJECTSHEETSID integer, ROADSHOULDERUSAGETYPE char(30), SEARESCUETOWERID integer, SAFETYBUOYLINEID integer, SLOPEGROUNDTYPE char(30), ONWANI_STREET_NAME char(30), DISTRICTBOUNDARYID integer, BUILDINGCOURTYARDID integer, NUMBEROFBUSHES integer, ORGVERREFSYSTEM char(250), NAMEPOPULARENGLISH char(500), PAVEMENT_TYPE char(30),
      FENCEID integer, CHIMNEYTYPE char(30), TELEPHONEBOOTHID integer, RLCWATTS char(30), ZARIBAHTYPE char(30), WALLSURFACEID integer, MISCMASTID integer, MONUMENTPROTECTIONTYPE char(30), ROADTUNNELTYPE char(30), AREACLASSIFICATIONCATEGORY integer, COMMUNITYID char(25), NAMEPOPULARARABIC char(500), PYLONID integer, NATIONALBOUNDARYID integer, MISCROADFURNITUREPOINTID integer, GEODETICCONTROLID integer, PLANNEDAREAMETRIC double, LANDTYPE char(30), POOLTYPE char(30), TRAFFICHUMPID integer, CYCLINGTRACKTYPE char(30), REMARK char(500), SLOPEID integer, TRAFFICSIGNALPOLETYPE char(30), RULEID integer, EMBANKMENTTYPE char(30), LINTELID integer, PILLARID integer, STREAMSURFACEID integer, STREAMWATERCOURSEEDGEID integer,
      NATIONALPOINTID integer, LISTEMIRATE char(30), PIPELINEID integer, MISCTELECOMMUNICATIONTYPE char(30), EMIRATEBOUNDARYID integer, ROADSIGNPOLEID integer, SLOPETYPE char(30), POOLOWNER char(30), BOLLARDMATERIAL char(30), OILWELLID integer, ALCHEIGHT char(30), ROAD_TYPE char(30), AREA_NAME char(30), CEMETRYID integer, BUILDINGINTERNALID integer, MEDIUMTYPE char(30), MISCROADFURNITURESURFACEID integer, MISCRFPOINT char(30), NUMBEROFBULBS char(30), GEODB_OID integer, FENCETREEID integer, DITCHSURFACEID integer, BUSLAYBYID integer, CONTOURLINEID integer, RADARTYPE char(30), SEASHOREID integer, SPORTFACILITYTYPE char(30), MODIFIEDBY char(30), PIPELINETYPE char(30), AREACLASSIFICATIONTYPE integer,
      DOLPHINID integer, SECCODE integer, ADVERTISEMENTSIGNID integer, WALLMOUNTEDBRACKETID integer, ADRSTREETID integer, CREATIONDATE char(14), RAILINGID integer, WELLTYPE char(30), MUNICIPALITYPOINTID integer, COMMUNITYPOINTID integer, RAMPTYPE char(30), SHELTERUSAGE char(30), BUILDINGUNDERGROUNDOUTLINEID integer, PUTTINGGREENID integer, PLANTING char(30), WASTEDISPOSALSITETYPE char(30), APPROVALCODE char(50), MARINEINSTRUMENTID integer, SIGNALLENSTYPE char(30), ADDRESSPLATETEXT char(50), DISTRICTARA char(50), TRACKID integer, BUOYTYPE char(30), BURIALDATEANDTIME char(14), POINTTYPE char(50), ROADSIGNTYPE char(50), COMMUNITYARA char(255), ROCKERYID integer, WALLTYPE char(30), GULLYDRAINAGETYPE char(30),
      LBCOLOR char(30), PHOTOURL char(500), RACETRACKUSE char(30), ALCWATTS char(30), BLDMCROOFSURFACEID integer, SHAPE_LEN00 double, ROADTYPE char(30), BLDROOFLINEID integer, DUCTMATERIALTYPE char(30), UPCID char(25), COASTALFCLTYSTRCTRTYPE char(30), ORNAMENTALFEATURETOPPOINTID integer, METROLINEBUILDINGID integer, ORIENTATION double, NAME char(500), INTERTIDALZONEID integer, VASEATTACHMENTTYPE char(30), ORIGNORTH double, ORIGHEIGHT double, COURTYARDTYPE char(30), BLDROOFSURFACEID integer, PLOTNUMBER char(50), TRACKTYPE char(30), WALLID integer, APPROVALDATE char(14), CURBSTONESTYLE char(30), BRIDGETYPE char(30), STARTDATE char(14), PROJECTID char(25), WITHCOLOR char(1),
      ELMSKEY char(255), DATE_RECEIVED char(14), DATEOFDEATH char(14), MISCMASTSURFACEID integer, UNITIDENTIFIER char(50), POPULATION double, MONUMENTMARKTYPE char(30), WELLUSAGE char(30), BLDMCHIGHESTPOINTID integer, Type char(16), Dataset_Name char(23), Geometry_Type char(8)
