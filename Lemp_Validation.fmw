FME workspace Lemp_Validation.fmw

Parameters:
- SourceDataset_DGNV8 = $(FME_MF_DIR)Haul_Road_Final.dgn   # Source Bentley MicroStation Design File(s)
- FEATURE_TYPES = BLDG Crest of embankment CULVERT Default Fences Pole Road_Centerline Road_Edge Road_Island Toe of embankment Tree Water
- DestDataset_DGNV8 = $(FME_MF_DIR)Error\Haul_Road_Error.dgn   # Destination Bentley MicroStation Design File

Readers:
- DGNV8_1: DGNV8 from $(SourceDataset_DGNV8)

Writers:
- DGNV8_2: DGNV8 to $(DestDataset_DGNV8)

Water (reader DGNV8_1)
    -> GeometryFilter
GeometryFilter
    FILTER_MODE = SIMPLE
    FILTER_MULTI = FILTER_TYPES]"Line Area"]FME_CONTROLLER_QUERY_FILE]]FME_CONTROLLER_CHOICE]Simple
    Curve -> Counter
    Curve -> Junction
    Curve -> TestFilter_5
    Curve -> Junction_2
    Curve -> TestFilter_17
    Area -> Counter
    Area -> Junction
    Area -> TestFilter_4
    Area -> Junction_2
    Area -> TestFilter_18
    <UNFILTERED> -> TestFilter_19
Junction
    -> GeometryValidator
    -> CoordinateExtractor
    -> GeometryValidator_2
    -> NeighborFinder_5 [CANDIDATE]
Counter
    CNT_ATTR = _count
    DOMAIN = counter
    SCOPE = Global
    START = 0
    -> Chopper
    -> TestFilter
    -> SpikeRemover
    -> CoordinateExtractor_2
Junction_2
    -> TestFilter_8
    -> TestFilter_9
    -> LineCombiner
    -> Chopper_5
Junction_4
    -> DGNStyler
Junction_5
    -> DGNStyler
DGNStyler
    COLOR_BY_LEVEL_DISPLAY = No
    COLOR_CHOICE_DISPLAY = RGB
    LINE_STYLE = 3
    LINE_WEIGHT = 4
    RGB_COLOR = 1,1,1
    RGB_FILL_COLOR = 1,1,1
    DGNStyled -> Water (writer DGNV8_2)
Water (writer DGNV8_2)

Bookmark: Self intesection check
GeometryValidator_2
    ISSUE_ATTR_NAME = _issues
    PRESETS = Custom
    REPAIR = No
    RULES = SELF_INTERSECTING CHECK_HOLE_TOUCHING_POLYGON]Yes]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NAN_REMOVAL PROCESS_MEASURE]NO]FME_CONTROLLER_QUERY_FILE]transformers/dependencies/geometryvalidator8/NAN_REMOVAL.fme]FME_CONTROLLER_CHOICE]NAN_REMOVAL
    SUMMARY = Detailed
    FAILED -> Counter_2
    ISSUE_LOCATIONS -> AttributeCreator_5
Counter_2
    CNT_ATTR = _count
    DOMAIN = counter
    GRP_CNT_ATTR = _idTemp
    SCOPE = Global
    START = 0
    -> Chopper_2
    -> Chopper_3
    -> FeatureMerger [REQUESTOR]
Chopper_2
    DEAGGREGATE_INPUT = Deaggregate
    MAX_VERTICES = 1
    MODE = By Vertex
    REMNANT_ATTR = _remnant
    CHOPPED -> CoordinateExtractor_3
CoordinateExtractor_3
    IND = 0
    MODE = Specify Coordinate
    X_ATTR = _x
    Y_ATTR = _y
    Z_ATTR = _z
    -> AttributeRounder
AttributeRounder
    PLACES = 2
    ROUND_TYPE = Nearest
    SRC_ATTRS = _x _y
    -> Matcher_3
Matcher_3
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _idTemp _x _y
    MATCH_STRATEGY = Match Selected Attributes
    SINGLE_MATCHED -> AttributeCreator_12
    SINGLE_MATCHED -> FeatureMerger [SUPPLIER]
AttributeCreator_12
    ATTR_TABLE = SET_TO igds_level_name (varchar(80)) = __Error__@Value(@Value(igds_level_name))
    -> Junction_3
Chopper_3
    DEAGGREGATE_INPUT = Deaggregate
    MAX_VERTICES = 2
    MODE = By Vertex
    REMNANT_ATTR = _remnant
    CHOPPED -> Matcher_4
Matcher_4
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _idTemp
    MATCH_STRATEGY = Match Selected Attributes
    SINGLE_MATCHED -> AttributeCreator_11
    SINGLE_MATCHED -> FeatureMerger [SUPPLIER]
FeatureMerger
    ATTR_ACCUM_MODE = Merge Supplier
    ATTR_CONFLICT_RES = Use Requestor
    IGNORE_NULLS = No
    JOIN_KEYS = @Value(_idTemp) @Value(_idTemp) AUTO
    LIST_ATTRS_TO_INCLUDE = _idTemp
    LIST_NAME = _List
    MERGE_TYPE = Attributes Only
    PROCESS_DUPS = NO
    REJECT_NULL_MISSING_KEYS = No
    SUPPLIERS_FIRST = No
    UNMERGED_REQUESTOR -> AttributeCreator_13
AttributeCreator_13
    ATTR_TABLE = SET_TO igds_level_name (varchar(80)) = __Error__@Value(@Value(igds_level_name))
    -> Junction_3
AttributeCreator_11
    ATTR_TABLE = SET_TO igds_level_name (varchar(80)) = __Error__@Value(@Value(igds_level_name))
    -> Junction_3
Junction_3
    -> DGNStyler
AttributeCreator_5
    ATTR_TABLE = SET_TO igds_level_name (varchar(80)) = __Error_@Value(issue_found)_@Value(@Value(igds_level_name))
    -> DGNStyler

Bookmark: Duplicate points
NeighborFinder_5
    CLOSE_LIST_ATTRS_TO_INCLUDE = igds_level_name
    CLOSE_LIST_ATTRS_TO_INCLUDE_MODE = Selected Attributes
    CLOSE_LIST_NAME = _proxyNode
    INSERT_VERTEX = No
    MAX = 0.1
    MEASURES_FROM_CANDIDATE = Yes
    MEASURE_TYPE = Continuous
    MODE = Candidates Only
    TREAT_POLYGON_AS = Lines
    MATCHED -> ListExploder_2
ListExploder_2
    ATTR_ACCUM_MODE = Prefix List Attributes
    INCOMING_PREFIX = _Proxy_
    INDEX_ATTR = _element_index
    LIST_ATTR = _proxyNode{}
    ELEMENTS -> TestFilter_15
TestFilter_15
    DEFAULT_VALUE = <UNFILTERED>
    PASSED_TEST_GROUP_OUTPUT = FIRST
    TEST_LIST = "BOOL_OP,OR,COMPOSITE_TEST,""""""1"""""",TEST_CLAUSE,TEST @Value(igds_level_name) = @Value(_Proxy_igds_level_name)",@Value(igds_level_name) = @Value(_Proxy_igds_level_name)
    @Value(igds_level_name) = @Value(_Proxy_igds_level_name) -> TestFilter_16
TestFilter_16
    DEFAULT_VALUE = <UNFILTERED>
    PASSED_TEST_GROUP_OUTPUT = FIRST
    TEST_LIST = "BOOL_OP,OR,COMPOSITE_TEST,""""""1"""""",TEST_CLAUSE,TEST @Value(_distance) = 0",@Value(_Proxy_distance) = 0
    <UNFILTERED> -> AttributeCreator_17
AttributeCreator_17
    ATTR_TABLE = SET_TO igds_level_name (varchar(80)) = __Error_duplicateVertices_@Value(igds_level_name)
    -> DGNStyler
    -> Inspector_5
Inspector_5
GeometryValidator
    ISSUE_ATTR_NAME = _issues
    PRESETS = Custom
    REPAIR = No
    RULES = CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D CONSECUTIVE_IDENTICAL_VERTICES_2D CHECK_Z]NO]TOLERANCE]0.01]FME_CONTROLLER_QUERY_FILE]transformers/dependencies/geometryvalidator8/CONSECUTIVE_IDENTICAL_VERTICES_2D.fme]FME_CONTROLLER_CHOICE]CONSECUTIVE_IDENTICAL_VERTICES_2D
    SUMMARY = Detailed
    ISSUE_LOCATIONS -> AttributeCreator
AttributeCreator
    ATTR_TABLE = SET_TO igds_level_name (buffer) = __Error_duplicatePoints
    -> Inspector
    -> DGNStyler
Inspector
CoordinateExtractor
    IND = 0
    MODE = Specify Coordinate
    X_ATTR = _x
    Y_ATTR = _y
    -> AttributeCreator_3
AttributeCreator_3
    ATTR_TABLE:
      SET_TO X (varchar(200)) = @round(@Value(@XValue()),2)
      SET_TO Y (varchar(200)) = @round(@Value(@XValue()),2)
    -> Matcher
Matcher
    BLANK_AND_MISSING_DIFFER = No
    CHECK_TYPES_AND_ENCODINGS = No
    CNT_ATTR = _match_id
    MATCHATTRS = igds_level_name X Y
    MATCH_STRATEGY = Match Selected Attributes
    SINGLE_MATCHED -> AttributeCreator_4
    SINGLE_MATCHED -> Inspector_4
Inspector_4
AttributeCreator_4
    ATTR_TABLE = SET_TO igds_level_name (varchar(80)) = __Error_duplicateVertex_@Value(igds_level_name)
    -> DGNStyler

Bookmark: Duplicate Segment
Chopper
    DEAGGREGATE_INPUT = Deaggregate
    MAX_VERTICES = 2
    MODE = By Vertex
    REMNANT_ATTR = _remnant
    CHOPPED -> Matcher_2
    CHOPPED -> LengthCalculator
    UNTOUCHED -> LengthCalculator
    UNTOUCHED -> Matcher_2
LengthCalculator
    DIM = 2
    LEN_ATTR = _length
    MULT = 1
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(_length) < 0.1",@Value(_length) < 0.1
    @Value(_length) < 0.1 -> AttributeCreator_9
AttributeCreator_9
    ATTR_TABLE = SET_TO igds_level_name (varchar(80)) = __Error_ShortSegments@Value(@Value(igds_level_name))
    -> DGNStyler
CoordinateExtractor_2
    IND = 0
    MODE = Specify Coordinate
    X_ATTR = _x
    Y_ATTR = _y
    Z_ATTR = _z
    -> AttributeCreator_6
AttributeCreator_6
    ATTR_TABLE:
      SET_TO XX (varchar(200)) = @round(@Value(@XValue()),2)
      SET_TO YY (varchar(200)) = @round((@YValue()),2)
      SET_TO ZZ (varchar(200)) = @round(@Value(@ZValue()),2)
    -> Matcher_2
Matcher_2
    BLANK_AND_MISSING_DIFFER = No
    BLANK_AND_MISSING_NAMES_TRAITS_DIFFER = No
    CHECK_COORDINATE_SYSTEMS = No
    CHECK_TYPES_AND_ENCODINGS = No
    CNT_ATTR = _match_id
    DIFFATTRS = igds_level_name
    LENIENT_MATCH = Yes
    MATCH = FULL
    MATCHATTRS = igds_level_name XX YY ZZ
    MATCH_STRATEGY = Match Selected Attributes
    SINGLE_MATCHED -> AttributeCreator_7
AttributeCreator_7
    ATTR_TABLE = SET_TO igds_level_name (buffer) = __Error_duplicateSegments@Value(@Value(igds_level_name))
    -> DGNStyler

Bookmark: Spike check
SpikeRemover
    DIMENSIONS = 2D
    ITERATIVE = Yes
    SPIKEANGLE = 10
    REMOVED -> AttributeCreator_2
AttributeCreator_2
    ATTR_TABLE = SET_TO igds_level_name (buffer) = __Error_Checkfor_Possible_Spike
    -> Inspector_2
    -> DGNStyler
Inspector_2

Bookmark: Unconnected elements
TestFilter
    DEFAULT_VALUE = <UNFILTERED>
    PASSED_TEST_GROUP_OUTPUT = FIRST
    TEST_LIST:
      "BOOL_OP,OR,COMPOSITE_TEST,""""""1 OR 2 OR 3 OR 4 OR 5 OR 6"""""",TEST_CLAUSE,TEST @Value(igds_level_name) = Road_Edge
      TEST @Value(igds_level_name) = Road_Centerline
      TEST @Value(igds_level_name) = Road_Island
      TEST @Value(igds_level_name) = Toe of embankment
      TEST @Value(igds_level_name) = Water
      TEST @Value(igds_level_name) = Crest of embankment",@Value(igds_level_name) = Road_Edge
    @Value(igds_level_name) = Road_Edge -> NodeValence [Line]
    @Value(igds_level_name) = Road_Edge -> TestFilter_10
    @Value(igds_level_name) = Road_Edge -> NeighborFinder_2 [CANDIDATE]
TestFilter_10
    DEFAULT_VALUE = <UNFILTERED>
    PASSED_TEST_GROUP_OUTPUT = FIRST
    TEST_LIST = "BOOL_OP,OR,COMPOSITE_TEST,""""""1"""""",TEST_CLAUSE,TEST @Value(fme_feature_type) = fme_polygon",@Value(fme_feature_type) = fme_polygon
    @Value(fme_feature_type) = fme_polygon -> Snipper
    <UNFILTERED> -> Snipper_2
Snipper
    DEAGGREGATE_INPUT = YES
    ENDVERTEXATTR = 0
    SNIPMODE = Vertex
    STARTVERTEXATTR = 0
    -> Counter_3
Snipper_2
    DEAGGREGATE_INPUT = YES
    ENDVERTEXATTR = -1
    SNIPMODE = Vertex
    STARTVERTEXATTR = -1
    -> Counter_3
Counter_3
    CNT_ATTR = _count
    DOMAIN = counter
    GRP_CNT_ATTR = _idVertex
    SCOPE = Global
    START = 0
    -> NeighborFinder_2 [BASE]
NeighborFinder_2
    CANDIDATES_FIRST = No
    CLOSE_LIST_ATTRS_TO_INCLUDE_MODE = Selected Attributes
    CLOSE_LIST_NAME = _List_segment
    INSERT_VERTEX = No
    MAX = 0.015
    MEASURES_FROM_CANDIDATE = Yes
    MEASURE_TYPE = Continuous
    MODE = Bases and Candidates
    TREAT_POLYGON_AS = Lines
    MATCHED -> ListExploder
ListExploder
    ATTR_ACCUM_MODE = Merge List Attributes
    ATTR_CONFLICT_RES = Use Original Attribute Values
    INDEX_ATTR = _element_index
    LIST_ATTR = _List_segment{}
    ELEMENTS -> TestFilter_11
TestFilter_11
    DEFAULT_VALUE = <UNFILTERED>
    PASSED_TEST_GROUP_OUTPUT = FIRST
    TEST_LIST = "BOOL_OP,OR,COMPOSITE_TEST,""""""1"""""",TEST_CLAUSE,TEST @Value(_distance) = 0",@Value(_distance) = 0
    @Value(_distance) = 0 -> FeatureJoiner [LEFT]
    <UNFILTERED> -> TestFilter_12
TestFilter_12
    DEFAULT_VALUE = <UNFILTERED>
    PASSED_TEST_GROUP_OUTPUT = FIRST
    TEST_LIST = "BOOL_OP,OR,COMPOSITE_TEST,""""""1"""""",TEST_CLAUSE,TEST @Value(_distance) > 0.001",@Value(_distance) > 0.001
    @Value(_distance) > 0.001 -> FeatureJoiner [LEFT]
    <UNFILTERED> -> FeatureJoiner [RIGHT]
FeatureJoiner
    ATTR_CONFLICT_RES = Prefer Left
    GEOMETRY_HANDLING = Prefer Left
    JOIN_KEYS = _idVertex _idVertex AUTO
    JOIN_MODE = Inner
    UNJOINED_LEFT -> AttributeCreator_14
AttributeCreator_14
    ATTR_TABLE = SET_TO igds_level_name (varchar(80)) = __Error_UnconnectedLines_@Value(igds_level_name)_
    -> Junction_4
NodeValence
    Node -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(valence) >= 2",@Value(valence) >= 2
LineCombiner
    ACCUM_ATTRS_NAME = Use Attributes From One Feature
    BREAK = no
    BREAK_CONNECTION_ATTRIBUTES = igds_level_name
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Chopper_4
    LINE -> PointOnLineOverlayer [LINE]
Chopper_4
    DEAGGREGATE_INPUT = Deaggregate
    MAX_VERTICES = 1
    MODE = By Vertex
    REMNANT_ATTR = _remnant
    CHOPPED -> PointOnLineOverlayer [POINT]
    CHOPPED -> NeighborFinder_3 [BASE]
PointOnLineOverlayer
    DEAGGREGATE_INPUT = Yes
    MEASURE_TYPE = Continuous
    MERGE_MEASURES = Yes
    OV_ATTR = _overlaps
    TOLERANCE = 0.01
    LINE -> NeighborFinder_4 [CANDIDATE]
Chopper_5
    DEAGGREGATE_INPUT = Deaggregate
    MAX_VERTICES = 1
    MODE = By Vertex
    REMNANT_ATTR = _remnant
    UNTOUCHED -> AttributeCreator_15
    UNTOUCHED -> NeighborFinder_3 [CANDIDATE]
NeighborFinder_3
    CANDIDATES_FIRST = No
    CLOSE_LIST_ATTRS_TO_INCLUDE = fme_feature_type
    CLOSE_LIST_ATTRS_TO_INCLUDE_MODE = Selected Attributes
    CLOSE_LIST_NAME = _closeElement
    INSERT_VERTEX = No
    MAX = .005
    MEASURES_FROM_CANDIDATE = Yes
    MEASURE_TYPE = Continuous
    MODE = Bases and Candidates
    TREAT_POLYGON_AS = Lines
    MATCHED -> ListElementCounter
ListElementCounter
    CNT_ATTR = _element_count
    LIST_NAME = _closeElement{}
    -> TestFilter_13
TestFilter_13
    DEFAULT_VALUE = <UNFILTERED>
    PASSED_TEST_GROUP_OUTPUT = FIRST
    TEST_LIST = "BOOL_OP,OR,COMPOSITE_TEST,""""""1"""""",TEST_CLAUSE,TEST @Value(_element_count) = 2",@Value(_element_count) =
    @Value(_element_count) = -> NeighborFinder_4 [BASE]
NeighborFinder_4
    CANDIDATES_FIRST = No
    CLOSE_LIST_ATTRS_TO_INCLUDE = fme_feature_type
    CLOSE_LIST_ATTRS_TO_INCLUDE_MODE = Selected Attributes
    CLOSE_LIST_NAME = _closeElement2
    INSERT_VERTEX = No
    MAX = .005
    MEASURES_FROM_CANDIDATE = Yes
    MEASURE_TYPE = Continuous
    MODE = Bases and Candidates
    TREAT_POLYGON_AS = Lines
    MATCHED -> ListElementCounter_2
ListElementCounter_2
    CNT_ATTR = _element_count2
    LIST_NAME = _closeElement2{}
    -> TestFilter_14
TestFilter_14
    DEFAULT_VALUE = <UNFILTERED>
    PASSED_TEST_GROUP_OUTPUT = FIRST
    TEST_LIST = "BOOL_OP,OR,COMPOSITE_TEST,""""""1"""""",TEST_CLAUSE,TEST @Value(_element_count2) = 2",@Value(_element_count) =
    @Value(_element_count) = -> AttributeCreator_16
AttributeCreator_16
    ATTR_TABLE = SET_TO igds_level_name (varchar(80)) = __Error_UnconnectedLines_@Value(igds_level_name)_
    -> Junction_4
AttributeCreator_15
    ATTR_TABLE = SET_TO igds_level_name (varchar(80)) = _Error_zeroLength Lne@Value(igds_level_name)
    -> Junction_4

Bookmark: Water Polygon Constant Height Check
TestFilter_4
    DEFAULT_VALUE = <UNFILTERED>
    PASSED_TEST_GROUP_OUTPUT = FIRST
    TEST_LIST = "BOOL_OP,OR,COMPOSITE_TEST,""""""1"""""",TEST_CLAUSE,TEST @Value(igds_level_name) = Water",@Value(igds_level_name) = Water
    @Value(igds_level_name) = Water -> GeometryValidator_3
GeometryValidator_3
    ISSUE_ATTR_NAME = _issues
    PRESETS = Custom
    REPAIR = No
    RULES = PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D CONSECUTIVE_IDENTICAL_VERTICES_2D CHECK_Z]NO]TOLERANCE]0.0]FME_CONTROLLER_QUERY_FILE]transformers/dependencies/geometryvalidator8/CONSECUTIVE_IDENTICAL_VERTICES_2D.fme]FME_CONTROLLER_CHOICE]CONSECUTIVE_IDENTICAL_VERTICES_2D SELF_INTERSECTING CHECK_HOLE_TOUCHING_POLYGON]Yes]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING
    SUMMARY = Detailed
    REPAIRED -> AttributeCreator_8
    ISSUE_LOCATIONS -> AttributeCreator_8
AttributeCreator_8
    ATTR_TABLE = SET_TO igds_level_name (varchar(80)) = __Error_Checkfor_@Value(@Value(issue_found))
    -> Inspector_3
    -> DGNStyler
Inspector_3

Bookmark: Intersecting Features
TestFilter_5
    DEFAULT_VALUE = <UNFILTERED>
    PASSED_TEST_GROUP_OUTPUT = FIRST
    TEST_LIST = "BOOL_OP,OR,COMPOSITE_TEST,""""""1"""""",TEST_CLAUSE,TEST @Value(igds_level_name) = CULVERT",@Value(igds_level_name) = CULVERT
    <UNFILTERED> -> LineOnLineOverlayer [LINE]
LineOnLineOverlayer
    ATTRS_ACCUM_MODE = Use Attributes From One Feature
    CLEANING_TOLERANCE = Automatic
    DEAGGREGATE_INPUT = Yes
    GENERATE_LIST_DROP = NO
    OV_ATTR = _overlaps
    SEPARATE_COLLINEAR_SEGMENTS = No
    POINT -> TestFilter_6
    LINE -> TestFilter_7
TestFilter_6
    DEFAULT_VALUE = <UNFILTERED>
    PASSED_TEST_GROUP_OUTPUT = FIRST
    TEST_LIST = "BOOL_OP,OR,COMPOSITE_TEST,""""""1"""""",TEST_CLAUSE,TEST @Value(_overlaps) > 1",@Value(_overlaps) > 1
    @Value(_overlaps) > 1 -> AttributeCreator_10
AttributeCreator_10
    ATTR_TABLE = SET_TO igds_level_name (varchar(80)) = __Error_crossing@Value(@Value(igds_level_name))
    -> DGNStyler
TestFilter_7
    DEFAULT_VALUE = <UNFILTERED>
    PASSED_TEST_GROUP_OUTPUT = FIRST
    TEST_LIST = "BOOL_OP,OR,COMPOSITE_TEST,""""""1"""""",TEST_CLAUSE,TEST @Value(_overlaps) > 1",@Value(_overlaps) > 1

Bookmark: LayerwiseGeometryCheck
TestFilter_19
    DEFAULT_VALUE = <UNFILTERED>
    PASSED_TEST_GROUP_OUTPUT = FIRST
    TEST_LIST:
      "BOOL_OP,OR,COMPOSITE_TEST,""""""1 OR 2"""""",TEST_CLAUSE,TEST @Value(igds_level_name) = Pole
      TEST @Value(igds_level_name) = Tree",@Value(igds_level_name) = Pole
    @Value(igds_level_name) = Pole -> TestFilter_20
    <UNFILTERED> -> AttributeCreator_20
TestFilter_20
    DEFAULT_VALUE = <UNFILTERED>
    PASSED_TEST_GROUP_OUTPUT = FIRST
    TEST_LIST = "BOOL_OP,OR,COMPOSITE_TEST,""""""1"""""",TEST_CLAUSE,TEST @Value(fme_geometry) = fme_point",@Value(fme_geometry) =
    <UNFILTERED> -> AttributeCreator_22
AttributeCreator_22
    ATTR_TABLE = SET_TO igds_level_name (varchar(80)) = __Error_WrongGeometry_@Value(igds_level_name)
    -> Junction_5
AttributeCreator_20
    ATTR_TABLE = SET_TO igds_level_name (varchar(80)) = __Error_WrongGeometry_@Value(igds_level_name)
    -> Junction_5
TestFilter_17
    DEFAULT_VALUE = <UNFILTERED>
    PASSED_TEST_GROUP_OUTPUT = FIRST
    TEST_LIST:
      "BOOL_OP,OR,COMPOSITE_TEST,""""""1 OR 2 OR 3 OR 4 OR 5 OR 6"""""",TEST_CLAUSE,TEST @Value(igds_level_name) = Crest of embankment
      TEST @Value(igds_level_name) = CULVERT
      TEST @Value(igds_level_name) = Fences
      TEST @Value(igds_level_name) = Road_Edge
      TEST @Value(igds_level_name) = Road_Island
      TEST @Value(igds_level_name) = Toe of embankment",@Value(igds_level_name) = Crest of embankment
    <UNFILTERED> -> AttributeCreator_23
AttributeCreator_23
    ATTR_TABLE = SET_TO igds_level_name (varchar(80)) = __Error_WrongGeometry_@Value(igds_level_name)
    -> Junction_5
TestFilter_18
    DEFAULT_VALUE = <UNFILTERED>
    PASSED_TEST_GROUP_OUTPUT = FIRST
    TEST_LIST:
      "BOOL_OP,OR,COMPOSITE_TEST,""""""1 OR 2"""""",TEST_CLAUSE,TEST @Value(igds_level_name) = BLDG
      TEST @Value(igds_level_name) = Water",@Value(igds_level_name) = BLDG
    @Value(igds_level_name) = BLDG -> AttributeCreator_21
AttributeCreator_21
    ATTR_TABLE = SET_TO igds_level_name (varchar(80)) = __Error_WrongGeometry_@Value(igds_level_name)
    -> Junction_5

Bookmark: Road Centerline missing
TestFilter_8
    DEFAULT_VALUE = <UNFILTERED>
    PASSED_TEST_GROUP_OUTPUT = FIRST
    TEST_LIST = "BOOL_OP,OR,COMPOSITE_TEST,""""""1"""""",TEST_CLAUSE,TEST @Value(igds_level_name) = Road_Centerline",@Value(igds_level_name) =
    @Value(igds_level_name) = -> Chopper_6
    @Value(igds_level_name) = -> NeighborFinder_6 [CANDIDATE]
Chopper_6
    DEAGGREGATE_INPUT = Deaggregate
    MAX_VERTICES = 2
    MODE = By Vertex
    REMNANT_ATTR = _remnant
    CHOPPED -> Snipper_3
Snipper_3
    DEAGGREGATE_INPUT = YES
    ENDLOCATIONATTR = 080
    MEASUREMENTTYPE = 2D
    SNIPMODE = Distance (Value)
    STARTLOCATIONATTR = 20
    -> NeighborFinder [BASE]
TestFilter_9
    DEFAULT_VALUE = <UNFILTERED>
    PASSED_TEST_GROUP_OUTPUT = FIRST
    TEST_LIST = "BOOL_OP,OR,COMPOSITE_TEST,""""""1"""""",TEST_CLAUSE,TEST @Value(igds_level_name) = Road_Edge",@Value(igds_level_name) = Road_Edge
    @Value(igds_level_name) = Road_Edge -> Chopper_7
    @Value(igds_level_name) = Road_Edge -> NeighborFinder [CANDIDATE]
NeighborFinder
    CANDIDATES_FIRST = No
    CLOSE_LIST_ATTRS_TO_INCLUDE = igds_level_name
    CLOSE_LIST_ATTRS_TO_INCLUDE_MODE = Selected Attributes
    CLOSE_LIST_NAME = _List_RC
    INSERT_VERTEX = No
    K = 1
    MAX = 10
    MEASURES_FROM_CANDIDATE = Yes
    MEASURE_TYPE = Continuous
    MODE = Bases and Candidates
    TREAT_POLYGON_AS = Lines
    UNMATCHED_BASE -> AttributeCreator_19
AttributeCreator_19
    ATTR_TABLE = SET_TO igds_level_name (varchar(80)) = __Error_ROadEdgeCenterLine_@Value(igds_level_name)_
    -> Junction_4
Chopper_7
    DEAGGREGATE_INPUT = Deaggregate
    MAX_VERTICES = 2
    MODE = By Vertex
    REMNANT_ATTR = _remnant
    CHOPPED -> Snipper_4
Snipper_4
    DEAGGREGATE_INPUT = YES
    ENDLOCATIONATTR = 080
    MEASUREMENTTYPE = 2D
    SNIPMODE = Distance (Value)
    STARTLOCATIONATTR = 20
    -> NeighborFinder_6 [BASE]
NeighborFinder_6
    CANDIDATES_FIRST = No
    CLOSE_LIST_ATTRS_TO_INCLUDE_MODE = Selected Attributes
    CLOSE_LIST_NAME = _List_RC_
    INSERT_VERTEX = No
    K = 1
    MAX = 10
    MEASURES_FROM_CANDIDATE = Yes
    MEASURE_TYPE = Continuous
    MODE = Bases and Candidates
    TREAT_POLYGON_AS = Lines
    UNMATCHED_BASE -> AttributeCreator_18
AttributeCreator_18
    ATTR_TABLE = SET_TO igds_level_name (varchar(80)) = __Error_ROadCenterLine_@Value(igds_level_name)_
    -> Junction_4

FME custom transformer NodeValence
Notes
    This transformer builds arc-node topology in attributes to mimic
    ARC/INFO
    Coverage network topology and adds 
    valence
    . See 
        topology_basics
    for some good diagrams and further discussion. After editing or filtering this process needs to be rerun, just like an
    ARC/INFO Build
    command to rebuild the correct relationships with new feature counts. The original system keys all ended in "#". The topology stack was stored as a series of layers inside a single dataset called a
    coverage
    .
    The lines have topology attributes exposed in the
    AAT
    table and nodes have attributes in the 
    NAT
    table, hence the suffix names 
    _aat
    and 
    _nat
    . The two featuretypes (lines and points) are intended to be considered as a single set. Not included in the
    AAT
    table is polygon topology which would contain the LPOLY# and RPOLY# identifiers.
    This process includes the equivalent of
    CLEAN
    which breaks all arcs at junctions, explodes all multiparts, removes all coincident lines and vertices.
    The addition of a 
    valence
    to the 
    NAT
    table is useful for analysis to classify
    dangles
    (1),
    pseudonodes
    (2),
    tees
    (3),
    intersections
    (4) or
    multiple junctions 
    (>4)
    .
    The arcs (lines) contain a foreign key to the 
    node_id
    in the 
    fnode
    and 
    tnode
    attributes to allow arcs to be tested for 
    direction 
    relative to the nodes.
    * Indexing the keys will be essential for reasonable performance when selecting or joining these two tables. Indexing in 
    ARC/INFO
    is implied because the original keys with a "#" in the name are the record number similiar to OBJECTID.
    * Tolerance defaults to 0.1 metre
    * The 
    arc_id
    is just one of the arcs joining the node as in the original model.
    * If arcs are not already split they will be split and therefore will duplicate existing attributes.
    * The fme_feature_ type is used to name the outputs the same as the source featuretype with a suffix _aat and _nat
Input is a branched polyline network <ft>
    Output is a cleaned line featuretype <ft>_aat and point representing nodes <ft>_nat
lines (PK arc_id) have fnode_id and tnode_id
nodes have node_id and valence and arc_id as first connecting arc
    Valence is a count of the number of arcs connecting at a node.

Note: Notes / This transformer builds arc-node topology in attributes to mimic ARC/INFO Coverage network topology and adds valence. See topology_basics for some good diagrams and further discussion. After editing or filtering this process needs to be rerun, just like an ARC/INFO Build command to rebuild the correct relationships with new feature counts. The original system keys all ended in "#". The topology stack was stored as a series of layers inside a single dataset called a coverage. / The lines have topology attributes exposed in the AAT table and nodes have attributes in the NAT table, hence the suffix names _aat and _nat. The two featuretypes (lines and points) are intended to be considered as a single set. Not included in the AAT table is polygon topology which would contain the LPOLY# and RPOLY# identifiers. / This process includes the equivalent of CLEAN which breaks all arcs at junctions, explodes all multiparts, removes all coincident lines and vertices. / The addition of a valence to the NAT table is useful for analysis to classify dangles (1), pseudonodes (2), tees (3), intersections (4) or multiple junctions (>4). / The arcs (lines) contain a foreign key to the node_id in the fnode and tnode attributes to allow arcs to be tested for direction relative to the nodes. / * Indexing the keys will be essential for reasonable performance when selecting or joining these two tables. Indexing in ARC/INFO is implied because the original keys with a "#" in the name are the record number similiar to OBJECTID. / * Tolerance defaults to 0.1 metre / * The arc_id is just one of the arcs joining the node as in the original model. / * If arcs are not already split they will be split and therefore will duplicate existing attributes. / * The fme_feature_ type is used to name the outputs the same as the source featuretype with a suffix _aat and _nat
Line (input)
    -> AttributeExposer

Bookmark: New Bookmark
Note: Splits arcs if not already split at intersections before assigning unique IDs which is transferred to the node. / Creates a point at every intersection and ends of every arc. Does not duplicate points at common junctions thank goodness / Adds a list of arcs connected to each node for the valence calculator
AttributeExposer
    ATTR_LIST = fme_feature_type
    -> First_Intersector
First_Intersector: Intersector
    DUPLICATE_Z_NODES = No
    LIST_NAME = all_reaches
    OV_ATTR = _overlaps
    PERFORM_SELF_INTERSECTION = No
    SEG_ATTR = _segments
    SEPARATE_COLLINEAR_SEGMENTS = No
    INTERSECTED -> arc_id_counter
arc_id_counter: Counter
    CNT_ATTR = arc_id
    DOMAIN = counter
    SCOPE = Local
    START = 1
    -> Intersector
Intersector
    DUPLICATE_Z_NODES = No
    LIST_NAME = all_reaches
    OV_ATTR = _overlaps
    PERFORM_SELF_INTERSECTION = No
    SEG_ATTR = _segments
    SEPARATE_COLLINEAR_SEGMENTS = No
    INTERSECTED -> Snipper_Begin
    INTERSECTED -> FeatureMerger_2 [REQUESTOR]
    NODE -> Node_id_counter

Bookmark: Distinguish between FNODE and TNODE (NeighborhoodPair does not)
Note: Snipper gets the first and last points. / Geohash is a spatial key to test for spatial coincidence with the nodes
Snipper_Begin
    ENDVERTEXATTR = 0
    SNIPMODE = Vertex
    STARTVERTEXATTR = 0
    -> Geohash_Begin
    REMNANTS -> Snipper_End
Geohash_Begin: GeometryExtractor
    ATTR = from_geohash
    GEOHASH_PRECISION_DISPLAY = ~9.3 mm (12 characters)
    KIND_LONG = Geohash
    -> FeatureMerger [REQUESTOR]
Snipper_End
    ENDVERTEXATTR = -1
    SNIPMODE = Vertex
    STARTVERTEXATTR = -1
    -> Geohash_End
Geohash_End: GeometryExtractor
    ATTR = to_geohash
    GEOHASH_PRECISION_DISPLAY = ~9.3 mm (12 characters)
    KIND_LONG = Geohash
    -> FeatureMerger_3 [REQUESTOR]
Geohash_node: GeometryExtractor
    ATTR = node_geohash
    GEOHASH_PRECISION_DISPLAY = ~9.3 mm (12 characters)
    KIND_LONG = Geohash
    -> FeatureMerger [SUPPLIER]
    -> FeatureMerger_3 [SUPPLIER]

Bookmark: Add node_id and valence
Node_id_counter: Counter
    CNT_ATTR = node_id
    DOMAIN = counter2
    SCOPE = Local
    START = 1
    -> ListElementCounter
Note: Valence
ListElementCounter
    CNT_ATTR = valence
    LIST_NAME = all_reaches{}
    -> AttributeKeeper
    -> Geohash_node
Note: Calculates the valence from the hidden list of arc-ids. / Output the nodes with unique ids. / arc_id is simply one of the connected arcs.
AttributeKeeper
    CREATE_BULK_MODE_FEATURES = No
    KEEP_ATTRS = arc_id,network_id,node_id,valence,fme_feature_type
    -> Node (output)

Bookmark: From Node
FeatureMerger
    ATTR_ACCUM_MODE = Merge Supplier
    ATTR_CONFLICT_RES = Use Requestor
    IGNORE_NULLS = No
    JOIN_KEYS = @Value(from_geohash) @Value(node_geohash) AUTO
    MERGE_TYPE = Attributes Only
    PROCESS_DUPS = No
    SUPPLIERS_FIRST = No
    MERGED -> AttributeCreator
Note: Join back the node_id as the from-node based on a Geohash match
AttributeCreator
    ATTR_LIST = fnode_id,@Value(node_id)
    -> AttributeKeeper_2
AttributeKeeper_2
    CREATE_BULK_MODE_FEATURES = No
    KEEP_ATTRS = arc_id,fnode_id
    -> FeatureMerger_2 [SUPPLIER]
FeatureMerger_2
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> FeatureMerger_4 [REQUESTOR]

Bookmark: To Node
FeatureMerger_3
    ATTR_ACCUM_MODE = Merge Supplier
    ATTR_CONFLICT_RES = Use Requestor
    IGNORE_NULLS = No
    JOIN_KEYS = @Value(to_geohash) @Value(node_geohash) AUTO
    MERGE_TYPE = Attributes Only
    PROCESS_DUPS = No
    SUPPLIERS_FIRST = No
    MERGED -> AttributeCreator_2
Note: Join back the node_id as the to-node based on a Geohash match
AttributeCreator_2
    ATTR_LIST = tnode_id,@Value(node_id)
    -> AttributeKeeper_3
AttributeKeeper_3
    CREATE_BULK_MODE_FEATURES = No
    KEEP_ATTRS = arc_id,tnode_id
    -> FeatureMerger_4 [SUPPLIER]
FeatureMerger_4
    ATTR_ACCUM_MODE = Merge Supplier
    ATTR_CONFLICT_RES = Use Requestor
    IGNORE_NULLS = No
    JOIN_KEYS = @Value(arc_id) @Value(arc_id) AUTO
    MERGE_TYPE = Attributes Only
    PROCESS_DUPS = No
    SUPPLIERS_FIRST = No
    MERGED -> AttributeRemover

Bookmark: Tidy temp attributes
AttributeRemover
    LIST_ATTRS = all_reaches{} all_reaches{}.arc_id all_reaches{}.direction all_reaches{}.fme_basename all_reaches{}.ID all_reaches{}.name all_reaches{}.network_id all_reaches{}.OBJECTID all_reaches{}.SHAPE_Length
    REMOVE_ATTRS = _overlaps,_segments
    -> Arc (output)
Arc (output)

Bookmark: Write Nodes
Node (output)
