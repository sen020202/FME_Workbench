FME workspace Aragon-Hydro-attri-Copy-02_SHP output.fmw

Parameters:
- DestDataset_SHAPEFILE =
- FEATURE_TYPES =
- FEATURE_TYPES_2 =
- SourceDataset_DGNV8 =
- SourceDataset_SHAPEFILE =

Readers:
- SHAPEFILE_1: SHAPEFILE from $(SourceDataset_SHAPEFILE)
- DGNV8_1: DGNV8 from $(SourceDataset_DGNV8)

Writers:
- SHAPEFILE_2: SHAPEFILE to $(DestDataset_SHAPEFILE)

Hydro-493 (reader SHAPEFILE_1)
    attributes: OBJECTID long, SITUACION varchar(5), CUENCA varchar(10), CLASIF varchar(5), CANALIZ varchar(5), ESTADO varchar(5), COMPONEN1D varchar(5), SUBCUENCA varchar(250), ID_HOJA varchar(5), NOMBRE varchar(250), NIVEL varchar(5), ID_Fenomen varchar(5), REGIMEN varchar(5), TIPO varchar(5), SHAPE_Leng double
    -> Counter_2
Counter_2
    CNT_ATTR = _count_ORI
    DOMAIN = counter
    SCOPE = Global
    START = 1
    -> Snipper
    -> FeatureJoiner [LEFT]
Snipper
    DEAGGREGATE_INPUT = YES
    ENDLOCATIONATTR = 99.5
    MEASUREMENTTYPE = 2D
    SNIPMODE = Distance (Percentage)
    STARTLOCATIONATTR = 0.5
    -> SpatialFilter_2 [Candidate]
Barranco de las Viñas (reader DGNV8_1)
    -> Counter
Counter
    CNT_ATTR = _count
    DOMAIN = counter
    SCOPE = Global
    START = 0
    -> AttributeFilter
AttributeFilter
    ATTR_NAME = igds_level_name
    ATTR_VALUES = <Empty>,<Missing>,<Null>,<Unfiltered>,Input_Hydro_Lines
    <UNFILTERED> -> Bufferer
Bufferer
    ANGLE = 22.5
    CAP_STYLE = Arc
    CORNER_STYLE = Arc
    MODE = AREA
    OFFSET = 0.001
    OFFSET_UNITS = NONE
    PRECISION = APPROX
    BUFFERED -> SpatialFilter_2 [Filter]
SpatialFilter_2
    AGGREGATE_HANDLING = Yes
    ATTR_ACCUM_MODE = Prefix Filter
    ATTR_PREFIX = _NOM_
    BASE_TYPE = Multiple Filters
    CURVE_BOUNDARY_RULE_PARAM = Default Rule
    PASS_CRITERIA = Pass Against One Filter
    PREDATTR = _predicate
    PREDICATES = INTERSECTS
    USE_BOUNDING_BOX = No
    PASSED -> FeatureJoiner [RIGHT]
FeatureJoiner
    ATTR_CONFLICT_RES = Use Left
    GEOMETRY_HANDLING = Use Left
    JOIN_KEYS = _count_ORI _count_ORI AUTO
    JOIN_MODE = Inner
    JOINED -> AttributeCreator
    UNJOINED_LEFT -> 518_Attribute_Updated_FME_GMM_Final (writer SHAPEFILE_2)
AttributeCreator
    ATTR_TABLE:
      SET_TO REGIMEN = PER
      SET_TO TIPO = @Substring(@Value(_NOM_igds_level_name),0,3)
      SET_TO NOMBRE = @Value(_NOM_igds_level_name)
    -> TestFilter
TestFilter
    DEFAULT_VALUE = <UNFILTERED>
    TEST_LIST:
      "BOOL_OP,OR,COMPOSITE_TEST,""""""1 OR 2 OR 3 OR 4 OR 5 OR 6 OR 7 OR 8 OR 9"""""",TEST_CLAUSE,CASE_INSENSITIVE_TEST @Value(TIPO) = BAR
      CASE_INSENSITIVE_TEST @Value(TIPO) = BSC
      CASE_INSENSITIVE_TEST @Value(TIPO) = OTR
      CASE_INSENSITIVE_TEST @Value(TIPO) = RAM
      CASE_INSENSITIVE_TEST @Value(TIPO) = RIE
      CASE_INSENSITIVE_TEST @Value(TIPO) = RIO
      CASE_INSENSITIVE_TEST @Value(TIPO) = SCL
      CASE_INSENSITIVE_TEST @Value(TIPO) = VAG
      CASE_INSENSITIVE_TEST @Value(TIPO) = Río",@Value(3) = BAR
    @Value(3) = BAR -> 518_Attribute_Updated_FME_GMM_Final (writer SHAPEFILE_2)
    <UNFILTERED> -> AttributeCreator_2
AttributeCreator_2
    ATTR_TABLE = SET_TO TIPO = RIO
    -> 518_Attribute_Updated_FME_GMM_Final (writer SHAPEFILE_2)
518_Attribute_Updated_FME_GMM_Final (writer SHAPEFILE_2)
    attributes: OBJECTID long, SITUACION varchar(5), CUENCA varchar(10), CLASIF varchar(5), CANALIZ varchar(5), ESTADO varchar(5), COMPONEN1D varchar(5), SUBCUENCA varchar(250), ID_HOJA varchar(5), NOMBRE varchar(250), NIVEL varchar(5), ID_Fenomen varchar(5), REGIMEN varchar(5), TIPO varchar(5), SHAPE_Leng double, fme_featur varchar(50)
