FME workspace geodatabase_file2none-IP_Ver-02.fmw

Parameters:
- SourceDataset_GEODATABASE_FILE = C:\JEGO\Sunshine\Client-Correction\14.08.2023\381\381.gdb   # INPUT_GDB_File Geodatabase
- DestDataset_GEODATABASE_FILE = C:\JEGO\Sunshine\Client-Correction\14.08.2023\381\OUT\381_Corrected.gdb   # OUTPUT_GDB_PATH_File Geodatabase
- DestDataset_ESRISHAPE = C:\JEGO\Sunshine\Client-Correction\14.08.2023\381\Err   # Destination Esri Shapefile Folder
- DestDataset_ESRISHAPE_5 = C:\JEGO\Sunshine\Client-Correction\14.08.2023\381\Err   # Destination Esri Shapefile Folder
- DestDataset_ESRISHAPE_7 = C:\JEGO\Sunshine\Client-Correction\14.08.2023\381\Err   # Destination Esri Shapefile Folder
- DestDataset_ESRISHAPE_6 = C:\JEGO\Sunshine\Client-Correction\14.08.2023\381\Err   # Destination Esri Shapefile Folder
- DestDataset_DGNV8 = C:\JEGO\Sunshine\Client-Correction\14.08.2023\381\Err\381_Error_01.dgn   # ERROR_DGN_Type_01
- DestDataset_DGNV8_5 = C:\JEGO\Sunshine\Client-Correction\14.08.2023\381\Err\381_Error_02.dgn   # ERROR_DGN_Type_02
- DestDataset_DGNV8_4 = H:\Exchange\manv\285_fme\Deaggregate_Error.dgn   # Destination Bentley MicroStation Design File

Readers:
- GEODATABASE_FILE_1: GEODATABASE_FILE from $(SourceDataset_GEODATABASE_FILE)

Writers:
- GEODATABASE_FILE_2: GEODATABASE_FILE to $(DestDataset_GEODATABASE_FILE)
- ESRISHAPE_1: ESRISHAPE to $(DestDataset_ESRISHAPE)
- ESRISHAPE_2: ESRISHAPE to $(DestDataset_ESRISHAPE_5)
- ESRISHAPE_3: ESRISHAPE to $(DestDataset_ESRISHAPE_7)
- ESRISHAPE_4: ESRISHAPE to $(DestDataset_ESRISHAPE_6)
- DGNV8_1: DGNV8 to $(DestDataset_DGNV8)
- DGNV8_2: DGNV8 to $(DestDataset_DGNV8_5)
- DGNV8_3: DGNV8 to $(DestDataset_DGNV8_4)

EdiPobCons_pol (reader GEODATABASE_FILE_1)
    attributes: objectid_2 integer, ID_Fenomen char(5), ESTADO char(5), ID_HOJA char(5), TIPO char(5), BIC char(5), CLASIF char(5), NOMBRE char(250), SITUACION char(5), USO char(5), C_NUCLEO_I char(14), D_NUCLEO_I char(80)
    -> Counter_3
    -> GeometryValidator
Counter_3
    CNT_ATTR = _count_EDI_POL
    DOMAIN = counter
    SCOPE = Global
    START = 1
    -> AreaCalculator_5
AreaCalculator_5
    AREA_ATTR = _area_Input
    AREA_TYPE = Plane Area
    MULT = 1
    -> VertexCounter_5
VertexCounter_5
    CNT_ATTR = _coordcount_Input
    -> GeometryValidator_4
    -> Matcher_3
GeometryValidator_4
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_10
    FAILED -> AttributeCreator_5
    REPAIRED -> Junction_10
    ISSUE_LOCATIONS -> AttributeCreator_6
    INVALID_PARTS -> AttributeCreator_6
AttributeCreator_5
    ATTR_TABLE = SET_TO G_Type = @Value(fme_feature_type)_Poly_Failed
    -> Junction_20
Junction_10
    -> VertexCounter_6
VertexCounter_6
    CNT_ATTR = _coordcount_OUTPUT
    -> AreaCalculator_6
    -> GeometryFilter_10
    -> Matcher_3
GeometryFilter_10
    BREAK_AGG = No
    GEOM_PORT_NAMES = Area
    AREA -> EdiPobCons_pol (writer GEODATABASE_FILE_2)
    <UNFILTERED> -> AttributeCreator_35
EdiPobCons_pol (writer GEODATABASE_FILE_2)
    attributes: ID_Fenomen char(5), ESTADO char(5), ID_HOJA char(5), TIPO char(5), BIC char(5), CLASIF char(5), NOMBRE char(250), SITUACION char(5), USO char(5), C_NUCLEO_I char(14), D_NUCLEO_I char(80)
AttributeCreator_35
    ATTR_TABLE = SET_TO Err_REASON = Wrong_Geometry_CHK_POLY
    -> Junction_19
AreaCalculator_6
    AREA_ATTR = _area_Output
    AREA_TYPE = Plane Area
    MULT = 1
    -> Tester_3
Tester_3
    BOOL_OP = AND
    COMPOSITE_TEST = 1 AND 2
    TEST_CLAUSE:
      TEST @Value(_coordcount_Input) = @Value(_coordcount_OUTPUT)
      TEST @Value(_area_Input) = @Value(_area_Output)
    TEST_MODE = TEST
    FAILED -> Junction_22
Matcher_3
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _count_EDI_POL
    MATCH_STRATEGY = Match Selected Attributes
    NOT_MATCHED -> AreaOnAreaOverlayer_3 [AREA]
AreaOnAreaOverlayer_3
    ACCUM_ATTRS_NAME = Use Attributes From One Feature
    CLEANING_TOLERANCE = Automatic
    CONNECT_Z_MODE = First Wins
    DEAGGREGATE_INPUT = Yes
    OVC_ATTR = _overlaps
    AREA -> Tester_21
    REMNANTS -> Junction_23
    <REJECTED> -> Junction_23
Tester_21
    BOOL_OP = OR
    COMPOSITE_TEST = 1
    TEST_CLAUSE = TEST @Value(_overlaps) = 1
    TEST_MODE = TEST
    PASSED -> Junction_23
    FAILED -> Tester_22
Tester_22
    BOOL_OP = OR
    COMPOSITE_TEST = 1
    TEST_CLAUSE = TEST @Value(_overlaps) = 2
    TEST_MODE = TEST
AttributeCreator_6
    ATTR_TABLE = SET_TO Geometry_type = Poly_Error
    -> Junction_18
RedViaria_pol (reader GEODATABASE_FILE_1)
    attributes: objectid_2 integer, ID_Fenomen char(5), ID_HOJA char(5), SITUACION char(5), ESTADOFIS char(5), TITULAR char(5), TIPO_TRAMO char(5), ORDEN char(5), NOMBRE char(250), NOMBRE_ALT char(250), ESTADO char(5), TIPO char(5), VIA char(5), CLASIF char(5)
    -> Counter_4
    -> GeometryValidator
Counter_4
    CNT_ATTR = _count_REDVIA_POL
    DOMAIN = counter
    SCOPE = Global
    START = 1
    -> AreaCalculator_7
AreaCalculator_7
    AREA_ATTR = _area_Input
    AREA_TYPE = Plane Area
    MULT = 1
    -> VertexCounter_7
VertexCounter_7
    CNT_ATTR = _coordcount_Input
    -> GeometryValidator_5
    -> Matcher_4
GeometryValidator_5
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_9
    FAILED -> AttributeCreator_7
    REPAIRED -> Junction_9
    ISSUE_LOCATIONS -> AttributeCreator_8
    INVALID_PARTS -> AttributeCreator_8
AttributeCreator_7
    ATTR_TABLE = SET_TO G_Type = @Value(fme_feature_type)_Poly_Failed
    -> Junction_20
Junction_9
    -> VertexCounter_8
VertexCounter_8
    CNT_ATTR = _coordcount_OUTPUT
    -> GeometryFilter_9
    -> AreaCalculator_11
    -> Matcher_4
GeometryFilter_9
    BREAK_AGG = No
    GEOM_PORT_NAMES = Area
    AREA -> RedViaria_pol (writer GEODATABASE_FILE_2)
    <UNFILTERED> -> AttributeCreator_36
RedViaria_pol (writer GEODATABASE_FILE_2)
    attributes: ID_Fenomen char(5), ID_HOJA char(5), SITUACION char(5), ESTADOFIS char(5), TITULAR char(5), TIPO_TRAMO char(5), ORDEN char(5), NOMBRE char(250), NOMBRE_ALT char(250), ESTADO char(5), TIPO char(5), VIA char(5)
AttributeCreator_36
    ATTR_TABLE = SET_TO Err_REASON = Wrong_Geometry_CHK_POLY
    -> Junction_19
AreaCalculator_11
    AREA_ATTR = _area_Output
    AREA_TYPE = Plane Area
    MULT = 1
    -> Tester_4
Tester_4
    BOOL_OP = AND
    COMPOSITE_TEST = 1 AND 2
    TEST_CLAUSE:
      TEST @Value(_coordcount_Input) = @Value(_coordcount_OUTPUT)
      TEST @Value(_area_Input) = @Value(_area_Output)
    TEST_MODE = TEST
    FAILED -> Junction_22
Matcher_4
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _count_REDVIA_POL
    MATCH_STRATEGY = Match Selected Attributes
    NOT_MATCHED -> AreaOnAreaOverlayer_4 [AREA]
AreaOnAreaOverlayer_4
    ACCUM_ATTRS_NAME = Use Attributes From One Feature
    CLEANING_TOLERANCE = Automatic
    CONNECT_Z_MODE = First Wins
    DEAGGREGATE_INPUT = Yes
    OVC_ATTR = _overlaps
    AREA -> Tester_23
    <REJECTED> -> Junction_23
Tester_23
    BOOL_OP = OR
    COMPOSITE_TEST = 1
    TEST_CLAUSE = TEST @Value(_overlaps) = 1
    TEST_MODE = TEST
    PASSED -> Junction_23
    FAILED -> Tester_24
Tester_24
    BOOL_OP = OR
    COMPOSITE_TEST = 1
    TEST_CLAUSE = TEST @Value(_overlaps) = 2
    TEST_MODE = TEST
    FAILED -> Junction_23
AttributeCreator_8
    ATTR_TABLE = SET_TO Geometry_type = Poly_Error
    -> Junction_18
CubiertaTer_pol (reader GEODATABASE_FILE_1)
    attributes: objectid_2 integer, ID_Fenomen char(5), ID_HOJA char(5), NOMBRE char(254), TIPO char(5), FIGURA char(5), CODIGO char(9)
    -> Counter_2
    -> GeometryValidator
Counter_2
    CNT_ATTR = _count_CUBER_POL
    DOMAIN = counter
    SCOPE = Global
    START = 1
    -> AreaCalculator_3
AreaCalculator_3
    AREA_ATTR = _area_Input
    AREA_TYPE = Plane Area
    MULT = 1
    -> VertexCounter_3
VertexCounter_3
    CNT_ATTR = _coordcount_Input
    -> GeometryValidator_3
    -> Matcher
GeometryValidator_3
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_11
    FAILED -> AttributeCreator_3
    REPAIRED -> Junction_11
    ISSUE_LOCATIONS -> AttributeCreator_4
    INVALID_PARTS -> AttributeCreator_4
AttributeCreator_3
    ATTR_TABLE = SET_TO G_Type = @Value(fme_feature_type)_Poly_Failed
    -> Junction_20
Junction_11
    -> VertexCounter_4
VertexCounter_4
    CNT_ATTR = _coordcount_OUTPUT
    -> GeometryFilter_11
    -> AreaCalculator_4
    -> Matcher
GeometryFilter_11
    BREAK_AGG = No
    GEOM_PORT_NAMES = Area
    AREA -> CubiertaTer_pol (writer GEODATABASE_FILE_2)
    <UNFILTERED> -> AttributeCreator_34
CubiertaTer_pol (writer GEODATABASE_FILE_2)
    attributes: OBJECTID char(9), ID_Fenomen char(5), ID_HOJA char(5), NOMBRE char(254), TIPO char(5), FIGURA char(5), CODIGO char(9)
AttributeCreator_34
    ATTR_TABLE = SET_TO Err_REASON = Wrong_Geometry_CHK_POLY
    -> Junction_19
AreaCalculator_4
    AREA_ATTR = _area_Output
    AREA_TYPE = Plane Area
    MULT = 1
    -> Tester_2
Tester_2
    BOOL_OP = AND
    COMPOSITE_TEST = 1 AND 2
    TEST_CLAUSE:
      TEST @Value(_coordcount_Input) = @Value(_coordcount_OUTPUT)
      TEST @Value(_area_Input) = @Value(_area_Output)
    TEST_MODE = TEST
    FAILED -> Junction_22
Matcher
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _count_CUBER_POL
    MATCH_STRATEGY = Match Selected Attributes
    NOT_MATCHED -> AreaOnAreaOverlayer [AREA]
AreaOnAreaOverlayer
    ACCUM_ATTRS_NAME = Use Attributes From One Feature
    CLEANING_TOLERANCE = Automatic
    CONNECT_Z_MODE = First Wins
    DEAGGREGATE_INPUT = Yes
    OVC_ATTR = _overlaps
    AREA -> Tester_17
    <REJECTED> -> Junction_23
Tester_17
    BOOL_OP = OR
    COMPOSITE_TEST = 1
    TEST_CLAUSE = TEST @Value(_overlaps) = 1
    TEST_MODE = TEST
    PASSED -> Junction_23
    FAILED -> Tester_18
Tester_18
    BOOL_OP = OR
    COMPOSITE_TEST = 1
    TEST_CLAUSE = TEST @Value(_overlaps) = 2
    TEST_MODE = TEST
    FAILED -> Junction_23
AttributeCreator_4
    ATTR_TABLE = SET_TO Geometry_type = Poly_Error
    -> Junction_18
EdiPobCons_lin (reader GEODATABASE_FILE_1)
    attributes: objectid_2 integer, ID_Fenomen char(5), ID_HOJA char(5), TIPO char(5), ESTADO char(5), BIC char(5), CLASIF char(5), SITUACION char(5), USO char(5), NOMBRE char(250)
    -> Counter_8
    -> GeometryValidator
Counter_8
    CNT_ATTR = _count_EDI_LIN
    DOMAIN = counter
    SCOPE = Global
    START = 1
    -> VertexCounter_15
VertexCounter_15
    CNT_ATTR = _coordcount_Input
    -> GeometryValidator_9
GeometryValidator_9
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_5
    FAILED -> AttributeCreator_15
    REPAIRED -> Junction_5
    ISSUE_LOCATIONS -> AttributeCreator_16
    INVALID_PARTS -> AttributeCreator_16
AttributeCreator_15
    ATTR_TABLE = SET_TO G_Type = @Value(fme_feature_type)_Line_Failed
    -> Junction_17
Junction_5
    -> VertexCounter_16
VertexCounter_16
    CNT_ATTR = _coordcount_OUTPUT
    -> Tester_8
    -> GeometryFilter_5
GeometryFilter_5
    BREAK_AGG = No
    GEOM_PORT_NAMES = Line
    LINE -> EdiPobCons_lin (writer GEODATABASE_FILE_2)
    <UNFILTERED> -> AttributeCreator_40
EdiPobCons_lin (writer GEODATABASE_FILE_2)
    attributes: ID_Fenomen char(5), ID_HOJA char(5), TIPO char(5), ESTADO char(5), BIC char(5), CLASIF char(5), SITUACION char(5), USO char(5), NOMBRE char(250)
AttributeCreator_40
    ATTR_TABLE = SET_TO Err_REASON = Wrong_Geometry_CHK_LINE
    -> Junction_19
Tester_8
    BOOL_OP = OR
    COMPOSITE_TEST = 1
    TEST_CLAUSE = TEST @Value(_coordcount_Input) = @Value(_coordcount_OUTPUT)
    TEST_MODE = TEST
    FAILED -> Junction_22
AttributeCreator_16
    ATTR_TABLE = SET_TO Geometry_type = Line_Error
    -> Junction_18
Hidrografia_lin (reader GEODATABASE_FILE_1)
    attributes: objectid_2 integer, SITUACION char(5), CUENCA char(10), CLASIF char(5), CANALIZ char(5), ESTADO char(5), COMPONEN1D char(5), SUBCUENCA char(250), ID_HOJA char(5), NOMBRE char(250), NIVEL char(5), ID_Fenomen char(5), REGIMEN char(5), TIPO char(5)
    -> Counter_9
    -> GeometryValidator
Counter_9
    CNT_ATTR = _count_HYDRO_LIN
    DOMAIN = counter
    SCOPE = Global
    START = 1
    -> VertexCounter_17
VertexCounter_17
    CNT_ATTR = _coordcount_Input
    -> GeometryValidator_10
GeometryValidator_10
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction
    FAILED -> AttributeCreator_17
    REPAIRED -> Junction
    ISSUE_LOCATIONS -> AttributeCreator_18
    INVALID_PARTS -> AttributeCreator_18
AttributeCreator_17
    ATTR_TABLE = SET_TO G_Type = @Value(fme_feature_type)_Line_Failed
    -> Junction_17
Junction
    -> VertexCounter_18
VertexCounter_18
    CNT_ATTR = _coordcount_OUTPUT
    -> Tester_9
    -> GeometryFilter
GeometryFilter
    BREAK_AGG = No
    GEOM_PORT_NAMES = Line
    LINE -> Hidrografia_lin (writer GEODATABASE_FILE_2)
    <UNFILTERED> -> AttributeCreator_41
Hidrografia_lin (writer GEODATABASE_FILE_2)
    attributes: SITUACION char(5), CUENCA char(10), CLASIF char(5), CANALIZ char(5), ESTADO char(5), COMPONEN1D char(5), SUBCUENCA char(250), ID_HOJA char(5), NOMBRE char(250), NIVEL char(5), ID_Fenomen char(5), REGIMEN char(5), TIPO char(5)
AttributeCreator_41
    ATTR_TABLE = SET_TO Err_REASON = Wrong_Geometry_CHK_LINE
    -> Junction_19
Tester_9
    BOOL_OP = OR
    COMPOSITE_TEST = 1
    TEST_CLAUSE = TEST @Value(_coordcount_Input) = @Value(_coordcount_OUTPUT)
    TEST_MODE = TEST
    FAILED -> Junction_22
AttributeCreator_18
    ATTR_TABLE = SET_TO Geometry_type = Line_Error
    -> Junction_18
LimiteAdministrativo_lin (reader GEODATABASE_FILE_1)
    attributes: objectid_2 integer, ID_Fenomen char(5), CODINE1 char(20), CODINE2 char(20), ENCLAVE1 char(20), ENCLAVE2 char(20), ID_LINLIM char(43), MUN1 char(250), MUN2 char(250), TIPO char(5), URL_RESOUR char(250), OBJECTID integer
    -> Counter_10
    -> GeometryValidator
Counter_10
    CNT_ATTR = _count_LIMITE_LIN
    DOMAIN = counter
    SCOPE = Global
    START = 1
    -> VertexCounter_19
VertexCounter_19
    CNT_ATTR = _coordcount_Input
    -> GeometryValidator_11
GeometryValidator_11
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_2
    FAILED -> AttributeCreator_19
    REPAIRED -> Junction_2
    ISSUE_LOCATIONS -> AttributeCreator_20
    INVALID_PARTS -> AttributeCreator_20
AttributeCreator_19
    ATTR_TABLE = SET_TO G_Type = @Value(fme_feature_type)_Line_Failed
    -> Junction_17
Junction_2
    -> VertexCounter_21
VertexCounter_21
    CNT_ATTR = _coordcount_OUTPUT
    -> GeometryFilter_2
    -> Tester_10
GeometryFilter_2
    BREAK_AGG = No
    GEOM_PORT_NAMES = Line
    LINE -> LimiteAdministrativo_lin (writer GEODATABASE_FILE_2)
    <UNFILTERED> -> AttributeCreator_42
LimiteAdministrativo_lin (writer GEODATABASE_FILE_2)
    attributes: ID_Fenomen char(5), CODINE1 char(20), CODINE2 char(20), ENCLAVE1 char(20), ENCLAVE2 char(20), ID_LINLIM char(43), MUN1 char(250), MUN2 char(250), TIPO char(5), URL_RESOUR char(250), OBJECTID integer
AttributeCreator_42
    ATTR_TABLE = SET_TO Err_REASON = Wrong_Geometry_CHK_LINE
    -> Junction_19
Tester_10
    BOOL_OP = OR
    COMPOSITE_TEST = 1
    TEST_CLAUSE = TEST @Value(_coordcount_Input) = @Value(_coordcount_OUTPUT)
    TEST_MODE = TEST
    FAILED -> Junction_22
AttributeCreator_20
    ATTR_TABLE = SET_TO Geometry_type = Line_Error
    -> Junction_18
NomGeo_lin (reader GEODATABASE_FILE_1)
    attributes: objectid_2 integer, ID_Fenomen char(5), CODIGO char(17), ENTIDAD char(250), FUENTE char(250), ID_HOJA char(5), IDIOMA char(5), NOMBRE char(250), ORIENTACIO char(20), TAMANO char(20)
    -> Counter_11
    -> GeometryValidator
Counter_11
    CNT_ATTR = _count_CUBER_POL
    DOMAIN = counter
    SCOPE = Global
    START = 1
    -> VertexCounter_20
VertexCounter_20
    CNT_ATTR = _coordcount_Input
    -> GeometryValidator_12
GeometryValidator_12
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_3
    FAILED -> AttributeCreator_21
    REPAIRED -> Junction_3
    ISSUE_LOCATIONS -> AttributeCreator_22
    INVALID_PARTS -> AttributeCreator_22
AttributeCreator_21
    ATTR_TABLE = SET_TO G_Type = @Value(fme_feature_type)_Line_Failed
    -> Junction_17
Junction_3
    -> VertexCounter_22
VertexCounter_22
    CNT_ATTR = _coordcount_OUTPUT
    -> GeometryFilter_3
    -> Tester_11
GeometryFilter_3
    BREAK_AGG = No
    GEOM_PORT_NAMES = Line
    LINE -> NomGeo_lin (writer GEODATABASE_FILE_2)
    <UNFILTERED> -> AttributeCreator_43
NomGeo_lin (writer GEODATABASE_FILE_2)
    attributes: ID_Fenomen char(5), CODIGO char(17), ENTIDAD char(250), FUENTE char(250), ID_HOJA char(5), IDIOMA char(5), NOMBRE char(250), ORIENTACIO char(20), TAMANO char(20)
AttributeCreator_43
    ATTR_TABLE = SET_TO Err_REASON = Wrong_Geometry_CHK_LINE
    -> Junction_19
Tester_11
    BOOL_OP = OR
    COMPOSITE_TEST = 1
    TEST_CLAUSE = TEST @Value(_coordcount_Input) = @Value(_coordcount_OUTPUT)
    TEST_MODE = TEST
    FAILED -> Junction_22
AttributeCreator_22
    ATTR_TABLE = SET_TO Geometry_type = Line_Error
    -> Junction_18
RedViaria_lin (reader GEODATABASE_FILE_1)
    attributes: objectid_2 integer, TITULAR char(5), NOMBRE char(250), FIRME char(5), LOCALIDAD char(80), TIPO_TRAMO char(5), FUENTE_V char(5), NOMBRE_CAT char(250), TIPO_VIAL char(5), DGC_VIA char(19), SITUACION char(5), FECHA_ALTA char(8), ID_VIAL char(15), ORDEN char(5), ID_Fenomen char(5), CLASE char(5), SENTIDO char(5), TIPO_VEHIC char(20), VELOCIDAD char(5), TIPO char(5), ESTADOFIS char(5), FECHA_BAJA char(8), ESTADO char(5), CODIGO char(15), ORIGEN_Z char(5), NCARRILES char(5), VIA char(5), CLASIF char(5), CALZADA char(5), ACCESO char(5),
      NOMBRE_ALT char(250), ID_TRAMO char(15), ANCHOCS char(5), ID_HOJA char(5), ITINERANCI char(20)
    -> Counter_12
    -> GeometryValidator
Counter_12
    CNT_ATTR = _count_REDVIA_LIN
    DOMAIN = counter
    SCOPE = Global
    START = 1
    -> VertexCounter_23
VertexCounter_23
    CNT_ATTR = _coordcount_Input
    -> GeometryValidator_13
GeometryValidator_13
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_4
    FAILED -> AttributeCreator_23
    REPAIRED -> Junction_4
    ISSUE_LOCATIONS -> AttributeCreator_24
    INVALID_PARTS -> AttributeCreator_24
AttributeCreator_23
    ATTR_TABLE = SET_TO G_Type = @Value(fme_feature_type)_Line_Failed
    -> Junction_17
Junction_4
    -> VertexCounter_24
VertexCounter_24
    CNT_ATTR = _coordcount_OUTPUT
    -> GeometryFilter_4
    -> Tester_12
GeometryFilter_4
    BREAK_AGG = No
    GEOM_PORT_NAMES = Line
    LINE -> RedViaria_lin (writer GEODATABASE_FILE_2)
    <UNFILTERED> -> AttributeCreator_44
RedViaria_lin (writer GEODATABASE_FILE_2)
    attributes: TITULAR char(5), NOMBRE char(250), FIRME char(5), LOCALIDAD char(80), TIPO_TRAMO char(5), FUENTE_V char(5), NOMBRE_CAT char(250), TIPO_VIAL char(5), DGC_VIA char(19), SITUACION char(5), FECHA_ALTA char(8), ID_VIAL char(15), ORDEN char(5), ID_Fenomen char(5), CLASE char(5), SENTIDO char(5), TIPO_VEHIC char(20), VELOCIDAD char(5), TIPO char(5), ESTADOFIS char(5), FECHA_BAJA char(8), ESTADO char(5), CODIGO char(15), ORIGEN_Z char(5), NCARRILES char(5), VIA char(5), CLASIF char(5), CALZADA char(5), ACCESO char(5), NOMBRE_ALT char(250),
      ID_TRAMO char(15), ANCHOCS char(5), ID_HOJA char(5), ITINERANCI char(20)
AttributeCreator_44
    ATTR_TABLE = SET_TO Err_REASON = Wrong_Geometry_CHK_LINE
    -> Junction_19
Tester_12
    BOOL_OP = OR
    COMPOSITE_TEST = 1
    TEST_CLAUSE = TEST @Value(_coordcount_Input) = @Value(_coordcount_OUTPUT)
    TEST_MODE = TEST
    FAILED -> Junction_22
AttributeCreator_24
    ATTR_TABLE = SET_TO Geometry_type = Line_Error
    -> Junction_18
Relieve_lin (reader GEODATABASE_FILE_1)
    attributes: objectid_2 integer, SONDA char(20), ID_HOJA char(5), SECCION char(5), TIPO char(5), COTA char(20), COMPONEN1D char(5), ID_Fenomen char(5), CLASIF char(5), ORIGEN char(20), PROCEDENCI char(5)
    -> Counter_13
    -> GeometryValidator
Counter_13
    CNT_ATTR = _count_RELIVE_LIN
    DOMAIN = counter
    SCOPE = Global
    START = 1
    -> VertexCounter_25
VertexCounter_25
    CNT_ATTR = _coordcount_Input
    -> GeometryValidator_14
GeometryValidator_14
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_13
    FAILED -> AttributeCreator_25
    REPAIRED -> Junction_13
    ISSUE_LOCATIONS -> AttributeCreator_26
    INVALID_PARTS -> AttributeCreator_26
AttributeCreator_25
    ATTR_TABLE = SET_TO G_Type = @Value(fme_feature_type)_Line_Failed
    -> Junction_17
Junction_13
    -> VertexCounter_26
VertexCounter_26
    CNT_ATTR = _coordcount_OUTPUT
    -> GeometryFilter_13
    -> Tester_13
GeometryFilter_13
    BREAK_AGG = No
    GEOM_PORT_NAMES = Line
    LINE -> Relieve_lin (writer GEODATABASE_FILE_2)
    <UNFILTERED> -> AttributeCreator_45
Relieve_lin (writer GEODATABASE_FILE_2)
    attributes: SONDA char(20), ID_HOJA char(5), SECCION char(5), TIPO char(5), COTA char(20), COMPONEN1D char(5), ID_Fenomen char(5), CLASIF char(5), ORIGEN char(20), PROCEDENCI char(5)
AttributeCreator_45
    ATTR_TABLE = SET_TO Err_REASON = Wrong_Geometry_CHK_LINE
    -> Junction_19
Tester_13
    BOOL_OP = OR
    COMPOSITE_TEST = 1
    TEST_CLAUSE = TEST @Value(_coordcount_Input) = @Value(_coordcount_OUTPUT)
    TEST_MODE = TEST
    FAILED -> Junction_22
AttributeCreator_26
    ATTR_TABLE = SET_TO Geometry_type = Line_Error
    -> Junction_18
ServInst_lin (reader GEODATABASE_FILE_1)
    attributes: objectid_2 integer, ID_Fenomen char(254), CODEXPLOT char(50), ESTADO char(5), ID_HOJA char(5), NOMBRE char(254), TIPO char(5), TITULAR char(254), SITUACION char(5), CLASIF char(5), CORONACION char(20), COTAMAX char(20)
    -> Counter_14
    -> GeometryValidator
Counter_14
    CNT_ATTR = _count_SERVICE_LIN
    DOMAIN = counter
    SCOPE = Global
    START = 1
    -> VertexCounter_27
VertexCounter_27
    CNT_ATTR = _coordcount_Input
    -> GeometryValidator_15
GeometryValidator_15
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_14
    FAILED -> AttributeCreator_27
    REPAIRED -> Junction_14
    ISSUE_LOCATIONS -> AttributeCreator_28
    INVALID_PARTS -> AttributeCreator_28
AttributeCreator_27
    ATTR_TABLE = SET_TO G_Type = @Value(fme_feature_type)_Line_Failed
    -> Junction_17
Junction_14
    -> VertexCounter_28
VertexCounter_28
    CNT_ATTR = _coordcount_OUTPUT
    -> GeometryFilter_14
    -> Tester_14
GeometryFilter_14
    BREAK_AGG = No
    GEOM_PORT_NAMES = Line
    LINE -> ServInst_lin (writer GEODATABASE_FILE_2)
    <UNFILTERED> -> AttributeCreator_46
ServInst_lin (writer GEODATABASE_FILE_2)
    attributes: ID_Fenomen char(254), CODEXPLOT char(50), ESTADO char(5), ID_HOJA char(5), NOMBRE char(254), TIPO char(5), TITULAR char(254), SITUACION char(5), CLASIF char(5), CORONACION char(20), COTAMAX char(20)
AttributeCreator_46
    ATTR_TABLE = SET_TO Err_REASON = Wrong_Geometry_CHK_LINE
    -> Junction_19
Tester_14
    BOOL_OP = OR
    COMPOSITE_TEST = 1
    TEST_CLAUSE = TEST @Value(_coordcount_Input) = @Value(_coordcount_OUTPUT)
    TEST_MODE = TEST
    FAILED -> Junction_22
AttributeCreator_28
    ATTR_TABLE = SET_TO Geometry_type = Line_Error
    -> Junction_18
CubiertaTer_lin (reader GEODATABASE_FILE_1)
    attributes: objectid_2 integer, ID_Fenomen char(5), ID_HOJA char(5), NOMBRE char(250), TIPO char(5)
    -> Counter_15
    -> GeometryValidator
Counter_15
    CNT_ATTR = _count_CUBER_LIN
    DOMAIN = counter
    SCOPE = Global
    START = 1
    -> VertexCounter_31
VertexCounter_31
    CNT_ATTR = _coordcount_Input
    -> GeometryValidator_16
GeometryValidator_16
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_15
    FAILED -> AttributeCreator_29
    REPAIRED -> Junction_15
    ISSUE_LOCATIONS -> AttributeCreator_30
    INVALID_PARTS -> AttributeCreator_30
AttributeCreator_29
    ATTR_TABLE = SET_TO G_Type = @Value(fme_feature_type)_Line_Failed
    -> Junction_17
Junction_15
    -> VertexCounter_29
VertexCounter_29
    CNT_ATTR = _coordcount_OUTPUT
    -> GeometryFilter_15
    -> Tester_15
GeometryFilter_15
    BREAK_AGG = No
    GEOM_PORT_NAMES = Line
    LINE -> CubiertaTer_lin (writer GEODATABASE_FILE_2)
    <UNFILTERED> -> AttributeCreator_47
CubiertaTer_lin (writer GEODATABASE_FILE_2)
    attributes: ID_Fenomen char(5), ID_HOJA char(5), NOMBRE char(250), TIPO char(5)
AttributeCreator_47
    ATTR_TABLE = SET_TO Err_REASON = Wrong_Geometry_CHK_LINE
    -> Junction_19
Tester_15
    BOOL_OP = OR
    COMPOSITE_TEST = 1
    TEST_CLAUSE = TEST @Value(_coordcount_Input) = @Value(_coordcount_OUTPUT)
    TEST_MODE = TEST
    FAILED -> Junction_22
AttributeCreator_30
    ATTR_TABLE = SET_TO Geometry_type = Line_Error
    -> Junction_18
RedFerro_lin (reader GEODATABASE_FILE_1)
    attributes: objectid integer, ID_Fenomen char(5), COMPONEN1D char(3), ANCHO_TIPO char(3), COMPETENCIA char(3), ELECTRIF char(3), ESTADO char(3), ID_HOJA char(5), ID_TRAMO char(15), NOMBRE char(250), NUMVIAS char(3), SITUACION char(3), TITULAR char(3), VELOCIDAD char(3), CODIGOF char(15), ID_TABLERO char(15), SHAPE_Length double
    -> Counter_16
    -> GeometryValidator
Counter_16
    CNT_ATTR = _count_REDFERRO_LIN
    DOMAIN = counter
    SCOPE = Global
    START = 1
    -> VertexCounter_32
VertexCounter_32
    CNT_ATTR = _coordcount_Input
    -> GeometryValidator_17
GeometryValidator_17
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_16
    FAILED -> AttributeCreator_31
    REPAIRED -> Junction_16
    ISSUE_LOCATIONS -> AttributeCreator_32
    INVALID_PARTS -> AttributeCreator_32
AttributeCreator_31
    ATTR_TABLE = SET_TO G_Type = @Value(fme_feature_type)_Line_Failed
    -> Junction_17
Junction_17
    -> Level1 (writer DGNV8_1)
Junction_16
    -> VertexCounter_30
VertexCounter_30
    CNT_ATTR = _coordcount_OUTPUT
    -> GeometryFilter_16
    -> Tester_16
GeometryFilter_16
    BREAK_AGG = No
    GEOM_PORT_NAMES = Line
    LINE -> RedFerro_lin (writer GEODATABASE_FILE_2)
    <UNFILTERED> -> AttributeCreator_48
RedFerro_lin (writer GEODATABASE_FILE_2)
    attributes: objectid integer, ID_Fenomen char(5), COMPONEN1D char(3), ANCHO_TIPO char(3), COMPETENCIA char(3), ELECTRIF char(3), ESTADO char(3), ID_HOJA char(5), ID_TRAMO char(15), NOMBRE char(250), NUMVIAS char(3), SITUACION char(3), TITULAR char(3), VELOCIDAD char(3), CODIGOF char(15), ID_TABLERO char(15), SHAPE_Length double
AttributeCreator_48
    ATTR_TABLE = SET_TO Err_REASON = Wrong_Geometry_CHK_LINE
    -> Junction_19
Tester_16
    BOOL_OP = OR
    COMPOSITE_TEST = 1
    TEST_CLAUSE = TEST @Value(_coordcount_Input) = @Value(_coordcount_OUTPUT)
    TEST_MODE = TEST
    FAILED -> Junction_22
AttributeCreator_32
    ATTR_TABLE = SET_TO Geometry_type = Line_Error
    -> Junction_18
Cuadricula_5k_pol (reader GEODATABASE_FILE_1)
    attributes: objectid_2 integer, ID_Fenomen char(5), CF_50K char(5), CF_5K char(5), HUSO char(20), ID_HOJA char(5), NOMBRE char(250), OBJECTID integer
    -> Counter
    -> GeometryValidator
Counter
    CNT_ATTR = _count_5K_POL
    DOMAIN = counter
    SCOPE = Global
    START = 1
    -> AreaCalculator
AreaCalculator
    AREA_ATTR = _area_Input
    AREA_TYPE = Plane Area
    MULT = 1
    -> VertexCounter
VertexCounter
    CNT_ATTR = _coordcount_Input
    -> GeometryValidator_2
    -> Matcher_2
GeometryValidator_2
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_12
    FAILED -> AttributeCreator
    REPAIRED -> Junction_12
    ISSUE_LOCATIONS -> AttributeCreator_2
    INVALID_PARTS -> AttributeCreator_2
AttributeCreator
    ATTR_TABLE = SET_TO G_Type = @Value(fme_feature_type)_Poly_Failed
    -> Junction_20
Junction_12
    -> VertexCounter_2
VertexCounter_2
    CNT_ATTR = _coordcount_OUTPUT
    -> GeometryFilter_12
    -> AreaCalculator_2
    -> Matcher_2
GeometryFilter_12
    BREAK_AGG = No
    GEOM_PORT_NAMES = Area
    AREA -> Cuadricula_5k_pol (writer GEODATABASE_FILE_2)
    <UNFILTERED> -> AttributeCreator_33
Cuadricula_5k_pol (writer GEODATABASE_FILE_2)
    attributes: OBJECTID integer, ID_Fenomen char(5), CF_50K char(5), CF_5K char(5), HUSO char(20), ID_HOJA char(5), NOMBRE char(250)
AttributeCreator_33
    ATTR_TABLE = SET_TO Err_REASON = Wrong_Geometry_CHK_POLY
    -> Junction_19
AreaCalculator_2
    AREA_ATTR = _area_Output
    AREA_TYPE = Plane Area
    MULT = 1
    -> Tester
Tester
    BOOL_OP = COMPOSITE
    COMPOSITE_TEST = 1 AND 2
    TEST_CLAUSE:
      TEST @Value(_coordcount_Input) = @Value(_coordcount_OUTPUT)
      TEST @Value(_area_Input) = @Value(_area_Output)
    TEST_MODE = TEST
    FAILED -> Junction_22
Matcher_2
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _count_5K_POL
    MATCH_STRATEGY = Match Selected Attributes
    NOT_MATCHED -> AreaOnAreaOverlayer_2 [AREA]
AreaOnAreaOverlayer_2
    ACCUM_ATTRS_NAME = Use Attributes From One Feature
    CLEANING_TOLERANCE = Automatic
    CONNECT_Z_MODE = First Wins
    DEAGGREGATE_INPUT = Yes
    OVC_ATTR = _overlaps
    AREA -> Tester_19
    <REJECTED> -> Junction_23
Tester_19
    BOOL_OP = OR
    COMPOSITE_TEST = 1
    TEST_CLAUSE = TEST @Value(_overlaps) = 1
    TEST_MODE = TEST
    PASSED -> Junction_23
    FAILED -> Tester_20
Tester_20
    BOOL_OP = OR
    COMPOSITE_TEST = 1
    TEST_CLAUSE = TEST @Value(_overlaps) = 2
    TEST_MODE = TEST
    FAILED -> Junction_23
AttributeCreator_2
    ATTR_TABLE = SET_TO Geometry_type = Poly_Error
    -> Junction_18
Hidrografia_pol (reader GEODATABASE_FILE_1)
    attributes: objectid_2 integer, SITUACION char(5), CUENCA char(10), CLASIF char(5), CANALIZ char(5), ESTADO char(5), ID_HOJA char(5), NOMBRE char(250), NIVEL char(5), TIPO char(5), SUBCUENCA char(250), REGIMEN char(5), ID_Fenomen char(5)
    -> Counter_5
    -> GeometryValidator
Counter_5
    CNT_ATTR = _count_HYDRO_POL
    DOMAIN = counter
    SCOPE = Global
    START = 1
    -> AreaCalculator_8
AreaCalculator_8
    AREA_ATTR = _area_Input
    AREA_TYPE = Plane Area
    MULT = 1
    -> VertexCounter_9
VertexCounter_9
    CNT_ATTR = _coordcount_Input
    -> GeometryValidator_6
    -> Matcher_5
GeometryValidator_6
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_8
    FAILED -> AttributeCreator_9
    REPAIRED -> Junction_8
    ISSUE_LOCATIONS -> AttributeCreator_10
    INVALID_PARTS -> AttributeCreator_10
AttributeCreator_9
    ATTR_TABLE = SET_TO G_Type = @Value(fme_feature_type)_Poly_Failed
    -> Junction_20
Junction_8
    -> VertexCounter_10
VertexCounter_10
    CNT_ATTR = _coordcount_OUTPUT
    -> GeometryFilter_8
    -> AreaCalculator_12
    -> Matcher_5
GeometryFilter_8
    BREAK_AGG = No
    GEOM_PORT_NAMES = Area
    AREA -> Hidrografia_pol (writer GEODATABASE_FILE_2)
    <UNFILTERED> -> AttributeCreator_37
Hidrografia_pol (writer GEODATABASE_FILE_2)
    attributes: SITUACION char(5), CUENCA char(10), CLASIF char(5), CANALIZ char(5), ESTADO char(5), ID_HOJA char(5), NOMBRE char(250), NIVEL char(5), TIPO char(5), SUBCUENCA char(250), REGIMEN char(5), ID_Fenomen char(5)
AttributeCreator_37
    ATTR_TABLE = SET_TO Err_REASON = Wrong_Geometry_CHK_POLY
    -> Junction_19
AreaCalculator_12
    AREA_ATTR = _area_Output
    AREA_TYPE = Plane Area
    MULT = 1
    -> Tester_6
Tester_6
    BOOL_OP = COMPOSITE
    COMPOSITE_TEST = 1 AND 2
    TEST_CLAUSE:
      TEST @Value(_coordcount_Input) = @Value(_coordcount_OUTPUT)
      TEST @Value(_area_Input) = @Value(_area_Output)
    TEST_MODE = TEST
    FAILED -> Junction_22
Matcher_5
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _count_HYDRO_POL
    MATCH_STRATEGY = Match Selected Attributes
    NOT_MATCHED -> AreaOnAreaOverlayer_5 [AREA]
AreaOnAreaOverlayer_5
    ACCUM_ATTRS_NAME = Use Attributes From One Feature
    CLEANING_TOLERANCE = Automatic
    CONNECT_Z_MODE = First Wins
    DEAGGREGATE_INPUT = Yes
    OVC_ATTR = _overlaps
    AREA -> Tester_25
    <REJECTED> -> Junction_23
Tester_25
    BOOL_OP = OR
    COMPOSITE_TEST = 1
    TEST_CLAUSE = TEST @Value(_overlaps) = 1
    TEST_MODE = TEST
    PASSED -> Junction_23
    FAILED -> Tester_26
Tester_26
    BOOL_OP = OR
    COMPOSITE_TEST = 1
    TEST_CLAUSE = TEST @Value(_overlaps) = 2
    TEST_MODE = TEST
    FAILED -> Junction_23
AttributeCreator_10
    ATTR_TABLE = SET_TO Geometry_type = Poly_Error
    -> Junction_18
ServInst_pol (reader GEODATABASE_FILE_1)
    attributes: objectid_2 integer, ID_Fenomen char(5), CODEXPLOT char(50), ESTADO char(5), ID_HOJA char(5), NOMBRE char(250), TIPO char(5), TITULAR char(5), SITUACION char(5), ENERGIA char(5), CORONACION char(20), COTAMAX char(20)
    -> Counter_6
    -> GeometryValidator
Counter_6
    CNT_ATTR = _count_SERVIC_POL
    DOMAIN = counter
    SCOPE = Global
    START = 1
    -> AreaCalculator_9
AreaCalculator_9
    AREA_ATTR = _area_Input
    AREA_TYPE = Plane Area
    MULT = 1
    -> VertexCounter_11
VertexCounter_11
    CNT_ATTR = _coordcount_Input
    -> GeometryValidator_7
    -> Matcher_6
GeometryValidator_7
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_7
    FAILED -> AttributeCreator_11
    REPAIRED -> Junction_7
    ISSUE_LOCATIONS -> AttributeCreator_12
    INVALID_PARTS -> AttributeCreator_12
AttributeCreator_11
    ATTR_TABLE = SET_TO G_Type = @Value(fme_feature_type)_Poly_Failed
    -> Junction_20
Junction_7
    -> VertexCounter_12
VertexCounter_12
    CNT_ATTR = _coordcount_OUTPUT
    -> GeometryFilter_7
    -> AreaCalculator_13
    -> Matcher_6
GeometryFilter_7
    BREAK_AGG = No
    GEOM_PORT_NAMES = Area
    AREA -> ServInst_pol (writer GEODATABASE_FILE_2)
    <UNFILTERED> -> AttributeCreator_38
ServInst_pol (writer GEODATABASE_FILE_2)
    attributes: ID_Fenomen char(5), CODEXPLOT char(50), ESTADO char(5), ID_HOJA char(5), NOMBRE char(250), TIPO char(5), TITULAR char(5), SITUACION char(5), ENERGIA char(5), CORONACION char(20), COTAMAX char(20)
AttributeCreator_38
    ATTR_TABLE = SET_TO Err_REASON = Wrong_Geometry_CHK_POLY
    -> Junction_19
AreaCalculator_13
    AREA_ATTR = _area_Output
    AREA_TYPE = Plane Area
    MULT = 1
    -> Tester_5
Tester_5
    BOOL_OP = COMPOSITE
    COMPOSITE_TEST = 1 AND 2
    TEST_CLAUSE:
      TEST @Value(_coordcount_Input) = @Value(_coordcount_OUTPUT)
      TEST @Value(_area_Input) = @Value(_area_Output)
    TEST_MODE = TEST
    FAILED -> Junction_22
Matcher_6
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _count_SERVIC_POL
    MATCH_STRATEGY = Match Selected Attributes
    NOT_MATCHED -> AreaOnAreaOverlayer_6 [AREA]
AreaOnAreaOverlayer_6
    ACCUM_ATTRS_NAME = Use Attributes From One Feature
    CLEANING_TOLERANCE = Automatic
    CONNECT_Z_MODE = First Wins
    DEAGGREGATE_INPUT = Yes
    OVC_ATTR = _overlaps
    AREA -> Tester_27
    <REJECTED> -> Junction_23
Tester_27
    BOOL_OP = OR
    COMPOSITE_TEST = 1
    TEST_CLAUSE = TEST @Value(_overlaps) = 1
    TEST_MODE = TEST
    PASSED -> Junction_23
    FAILED -> Tester_28
Tester_28
    BOOL_OP = OR
    COMPOSITE_TEST = 1
    TEST_CLAUSE = TEST @Value(_overlaps) = 2
    TEST_MODE = TEST
    FAILED -> Junction_23
AttributeCreator_12
    ATTR_TABLE = SET_TO Geometry_type = Poly_Error
    -> Junction_18
RedFerro_pol (reader GEODATABASE_FILE_1)
    attributes: objectid integer, ID_Fenomen char(5), ID_HOJA char(5), CODIGOF char(250), ID_TABLERO char(15), SHAPE_Length double, SHAPE_Area double
    -> Counter_7
    -> GeometryValidator
Counter_7
    CNT_ATTR = _count_REDFERRO_POL
    DOMAIN = counter
    SCOPE = Global
    START = 1
    -> AreaCalculator_10
AreaCalculator_10
    AREA_ATTR = _area_Input
    AREA_TYPE = Plane Area
    MULT = 1
    -> VertexCounter_13
VertexCounter_13
    CNT_ATTR = _coordcount_Input
    -> GeometryValidator_8
    -> Matcher_7
GeometryValidator_8
    ISSUE_ATTR_NAME = _issues
    PRESETS = Custom
    REPAIR = Yes
    RULES = CONSECUTIVE_IDENTICAL_VERTICES_2D CHECK_Z]YES]TOLERANCE]0.01]FME_CONTROLLER_QUERY_FILE]transformers/dependencies/geometryvalidator/CONSECUTIVE_IDENTICAL_VERTICES_2D.fme SELF_INTERSECTING CHECK_HOLE_TOUCHING_POLYGON]No]CONNECT_Z_MODE_SI]FIRST_WINS]SELF_INTERSECTION_TOLERANCE]0.01]FME_CONTROLLER_QUERY_FILE]transformers/dependencies/geometryvalidator/SELF_INTERSECTING.fme
    SUMMARY = Detailed
    PASSED -> Junction_6
    FAILED -> AttributeCreator_13
    REPAIRED -> Junction_6
    ISSUE_LOCATIONS -> AttributeCreator_14
    INVALID_PARTS -> AttributeCreator_14
AttributeCreator_13
    ATTR_TABLE = SET_TO G_Type = @Value(fme_feature_type)_Poly_Failed
    -> Junction_20
Junction_20
    -> Level1 (writer DGNV8_1)
Level1 (writer DGNV8_1)
    attributes: G_Type char(200), objectid_2 integer, ID_Fenomen char(5), ID_HOJA char(5), NOMBRE char(250), TIPO char(5), FIGURA char(5), CODIGO char(15), _count_CUBER_POL char(200), _area_Input char(200), _coordcount_Input char(200), _issues{}.count char(200), _issues{}.issue_found char(200), _issues{}.location_sample.x char(200), _issues{}.location_sample.y char(200), _issues{}.location_sample.z char(200), _issues{}.repair_state char(200), SITUACION char(5), CUENCA char(10), CLASIF char(5), CANALIZ char(5), ESTADO char(5), NIVEL char(5), SUBCUENCA char(250), REGIMEN char(5), _count_HYDRO_POL char(200), objectid integer, CODIGOF char(15), ID_TABLERO char(15), SHAPE_Length double,
      SHAPE_Area double, _count_REDFERRO_POL char(200), CF_50K char(5), CF_5K char(5), HUSO char(20), OBJECTID integer, _count_5K_POL char(200), ESTADOFIS char(5), TITULAR char(3), TIPO_TRAMO char(5), ORDEN char(5), NOMBRE_ALT char(250), VIA char(5), _count_REDVIA_POL char(200), CODEXPLOT char(50), ENERGIA char(5), CORONACION char(20), COTAMAX char(20), _count_SERVIC_POL char(200), BIC char(5), USO char(5), C_NUCLEO_I char(14), D_NUCLEO_I char(80), _count_EDI_POL char(200), _count_CUBER_LIN char(200), CODINE1 char(200), CODINE2 char(200), ENCLAVE1 char(200), ENCLAVE2 char(200), ID_LINLIM char(200),
      MUN1 char(200), MUN2 char(200), URL_RESOUR char(200), _count_LIMITE_LIN char(200), ENTIDAD char(200), FUENTE char(200), IDIOMA char(200), ORIENTACIO char(200), TAMANO char(200), _count_EDI_LIN char(200), COMPONEN1D char(200), _count_HYDRO_LIN char(200), _count_SERVICE_LIN char(200), SONDA char(200), SECCION char(200), COTA char(200), ORIGEN char(200), PROCEDENCI char(200), _count_RELIVE_LIN char(200), FIRME char(200), LOCALIDAD char(200), FUENTE_V char(200), NOMBRE_CAT char(200), TIPO_VIAL char(200), DGC_VIA char(200), FECHA_ALTA char(200), ID_VIAL char(200), CLASE char(200), SENTIDO char(200), TIPO_VEHIC char(200),
      VELOCIDAD char(200), FECHA_BAJA char(200), ORIGEN_Z char(200), NCARRILES char(200), CALZADA char(200), ACCESO char(200), ID_TRAMO char(200), ANCHOCS char(200), ITINERANCI char(200), _count_REDVIA_LIN char(200), ANCHO_TIPO char(200), COMPETENCIA char(200), ELECTRIF char(200), NUMVIAS char(200), _count_REDFERRO_LIN char(200)
Junction_6
    -> VertexCounter_14
VertexCounter_14
    CNT_ATTR = _coordcount_OUTPUT
    -> AreaCalculator_14
    -> GeometryFilter_6
    -> Matcher_7
GeometryFilter_6
    BREAK_AGG = No
    GEOM_PORT_NAMES = Area
    AREA -> RedFerro_pol (writer GEODATABASE_FILE_2)
    <UNFILTERED> -> AttributeCreator_39
RedFerro_pol (writer GEODATABASE_FILE_2)
    attributes: objectid integer, ID_Fenomen char(5), ID_HOJA char(5), CODIGOF char(250), ID_TABLERO char(15), SITUACION char(5), NOMBRE char(5), COMPONED2D char(5)
AttributeCreator_39
    ATTR_TABLE = SET_TO Err_REASON = Wrong_Geometry_CHK_POLY
    -> Junction_19
Junction_19
    -> Inspector_3
    -> GeometryFilter_19
GeometryFilter_19
    BREAK_AGG = No
    GEOM_PORT_NAMES = Point Line Area
    LINE -> Shapefile1 (writer ESRISHAPE_3)
    <UNFILTERED> -> Shapefile1 (writer ESRISHAPE_3)
Shapefile1 (writer ESRISHAPE_3)
    attributes: Err_REASON char(200), objectid_2 long, ID_Fenomen char(5), ID_HOJA char(5), NOMBRE char(250), TIPO char(5), _count_CUB char(200), _coordcoun char(200), _coordco00 char(200), objectid long, CODIGOF char(250), ID_TABLERO char(15), SHAPE_Leng double, SHAPE_Area double, SITUACION char(5), ESTADOFIS char(5), TITULAR char(5), TIPO_TRAMO char(5), ORDEN char(5), NOMBRE_ALT char(250), ESTADO char(5), VIA char(5), CLASIF char(5), CODINE1 char(20), CODINE2 char(20), ENCLAVE1 char(20), ENCLAVE2 char(20), ID_LINLIM char(43), MUN1 char(250), MUN2 char(250),
      URL_RESOUR char(250), OBJECTID long, FIGURA char(5), CODIGO char(9), CODEXPLOT char(50), ENERGIA char(5), CORONACION char(20), COTAMAX char(20), CUENCA char(10), CANALIZ char(5), NIVEL char(5), SUBCUENCA char(250), REGIMEN char(5), BIC char(5), USO char(5), C_NUCLEO_I char(14), D_NUCLEO_I char(80), SONDA char(20), SECCION char(5), COTA char(20), COMPONEN1D char(5), ORIGEN char(20), PROCEDENCI char(5), CF_50K char(5), CF_5K char(5), HUSO char(20), _count_5K_ char(200), FIRME char(5), LOCALIDAD char(80), FUENTE_V char(5),
      NOMBRE_CAT char(250), TIPO_VIAL char(5), DGC_VIA char(19), FECHA_ALTA char(8), ID_VIAL char(15), CLASE char(5), SENTIDO char(5), TIPO_VEHIC char(20), VELOCIDAD char(5), FECHA_BAJA char(8), ORIGEN_Z char(5), NCARRILES char(5), CALZADA char(5), ACCESO char(5), ID_TRAMO char(15), ANCHOCS char(5), ITINERANCI char(20), ENTIDAD char(250), FUENTE char(250), IDIOMA char(5), ORIENTACIO char(20), TAMANO char(20), ANCHO_TIPO char(3), COMPETENCI char(3), ELECTRIF char(3), NUMVIAS char(3)
Inspector_3
AreaCalculator_14
    AREA_ATTR = _area_Output
    AREA_TYPE = Plane Area
    MULT = 1
    -> Tester_7
Tester_7
    BOOL_OP = COMPOSITE
    COMPOSITE_TEST = 1 AND 2
    TEST_CLAUSE:
      TEST @Value(_coordcount_Input) = @Value(_coordcount_OUTPUT)
      TEST @Value(_area_Input) = @Value(_area_Output)
    TEST_MODE = TEST
    FAILED -> Junction_22
Junction_22
    -> COUNT_MISMATCH_OBJECTS
COUNT_MISMATCH_OBJECTS: Inspector
Matcher_7
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _count_REDFERRO_POL
    MATCH_STRATEGY = Match Selected Attributes
    NOT_MATCHED -> AreaOnAreaOverlayer_7 [AREA]
AreaOnAreaOverlayer_7
    ACCUM_ATTRS_NAME = Use Attributes From One Feature
    CLEANING_TOLERANCE = Automatic
    CONNECT_Z_MODE = First Wins
    DEAGGREGATE_INPUT = Yes
    OVC_ATTR = _overlaps
    AREA -> Tester_29
    <REJECTED> -> Junction_23
Tester_29
    BOOL_OP = OR
    COMPOSITE_TEST = 1
    TEST_CLAUSE = TEST @Value(_overlaps) = 1
    TEST_MODE = TEST
    PASSED -> Junction_23
    FAILED -> Tester_30
Tester_30
    BOOL_OP = OR
    COMPOSITE_TEST = 1
    TEST_CLAUSE = TEST @Value(_overlaps) = 2
    TEST_MODE = TEST
    FAILED -> Junction_23
Junction_23
    -> GeometryFilter_20
GeometryFilter_20
    BREAK_AGG = No
    GEOM_PORT_NAMES = Point Line Area
    POINT -> PointOnPointOverlayer [POINT]
    LINE -> LengthCalculator
    AREA -> AreaCalculator_15
PointOnPointOverlayer
    DEAGGREGATE_INPUT = Yes
    OV_ATTR = _overlaps_POINT
    TOLERANCE = 0.001
    POINT -> Tester_31
Tester_31
    BOOL_OP = OR
    COMPOSITE_TEST = 1
    TEST_CLAUSE = TEST @Value(_overlaps_POINT) = 1
    TEST_MODE = TEST
    PASSED -> AttributeCreator_49
LengthCalculator
    DIM = 2
    LEN_ATTR = _length
    MULT = 1
    -> DuplicateFilter
DuplicateFilter
    INPUT_ORDERED_CHOICE = No
    KEYATTR = _length
    UNIQUE -> AttributeCreator_49
AreaCalculator_15
    AREA_ATTR = _area_DUP
    AREA_TYPE = Plane Area
    MULT = 1
    -> DuplicateFilter_2
DuplicateFilter_2
    INPUT_ORDERED_CHOICE = No
    KEYATTR = _area_DUP
    UNIQUE -> AttributeCreator_49
AttributeCreator_49
    ATTR_TABLE = SET_TO igds_level_name = @Value(fme_feature_type)_Errors_Doubt
    -> Inspector
    -> Level1 (writer DGNV8_2)
Level1 (writer DGNV8_2)
    attributes: objectid_2 integer, ID_Fenomen char(5), ID_HOJA char(5), SITUACION char(5), ESTADOFIS char(5), TITULAR char(5), TIPO_TRAMO char(5), ORDEN char(5), NOMBRE char(254), NOMBRE_ALT char(250), ESTADO char(5), TIPO char(5), VIA char(5), CLASIF char(5), _count_REDVIA_POL char(200), _area_Input char(200), _coordcount_Input char(200), _issues{}.count char(200), _issues{}.issue_found char(200), _issues{}.location_sample.x char(200), _issues{}.location_sample.y char(200), _issues{}.location_sample.z char(200), _coordcount_OUTPUT char(200), _overlaps char(200), objectid integer, CODIGOF char(250), ID_TABLERO char(15), SHAPE_Length double, SHAPE_Area double, _count_REDFERRO_POL char(200),
      CF_50K char(5), CF_5K char(5), HUSO char(20), OBJECTID integer, _count_5K_POL char(200), fme_rejection_code char(200), CUENCA char(10), CANALIZ char(5), NIVEL char(5), SUBCUENCA char(250), REGIMEN char(5), _count_HYDRO_POL char(200), FIGURA char(5), CODIGO char(9), _count_CUBER_POL char(200), BIC char(5), USO char(5), C_NUCLEO_I char(14), D_NUCLEO_I char(80), _count_EDI_POL char(200), CODEXPLOT char(50), ENERGIA char(5), CORONACION char(20), COTAMAX char(20), _count_SERVIC_POL char(200), _overlaps_POINT char(200), _length char(200), _area_DUP char(200)
Inspector
AttributeCreator_14
    ATTR_TABLE = SET_TO Geometry_type = Poly_Error
    -> Junction_18
Junction_18
    -> Shapefile1 (writer ESRISHAPE_2)
    -> Inspector_2
Shapefile1 (writer ESRISHAPE_2)
    attributes: Geometry_t char(200), objectid_2 long, SONDA char(20), ID_HOJA char(5), SECCION char(5), TIPO char(5), COTA char(20), COMPONEN1D char(5), ID_Fenomen char(5), CLASIF char(5), ORIGEN char(20), PROCEDENCI char(5), _count_REL char(200), _coordcoun char(200), count char(200), details char(200), issue_foun char(200), _issues___ char(200), _issues_00 char(200), _issues_01 char(200), _issues_02 char(200), _issues_03 char(200), _issues_04 char(200), NOMBRE char(250), _count_CUB char(200), FIGURA char(5), CODIGO char(9), _count_C00 char(200), _area_Inpu char(200), TITULAR char(5),
      FIRME char(5), LOCALIDAD char(80), TIPO_TRAMO char(5), FUENTE_V char(5), NOMBRE_CAT char(250), TIPO_VIAL char(5), DGC_VIA char(19), SITUACION char(5), FECHA_ALTA char(8), ID_VIAL char(15), ORDEN char(5), CLASE char(5), SENTIDO char(5), TIPO_VEHIC char(20), VELOCIDAD char(5), ESTADOFIS char(5), FECHA_BAJA char(8), ESTADO char(5), ORIGEN_Z char(5), NCARRILES char(5), VIA char(5), CALZADA char(5), ACCESO char(5), NOMBRE_ALT char(250), ID_TRAMO char(15), ANCHOCS char(5), ITINERANCI char(20), _count_RED char(200), objectid long, CODIGOF char(250),
      ID_TABLERO char(15), SHAPE_Leng double, SHAPE_Area double, _count_R00 char(200), BIC char(5), USO char(5), _count_EDI char(200), CUENCA char(10), CANALIZ char(5), SUBCUENCA char(250), NIVEL char(5), REGIMEN char(5), _count_HYD char(200), _count_H00 char(200), CODEXPLOT char(50), ENERGIA char(5), CORONACION char(20), COTAMAX char(20), _count_SER char(200), _count_S00 char(200), _count_R01 char(200), ANCHO_TIPO char(3), COMPETENCI char(3), ELECTRIF char(3), NUMVIAS char(3), _count_R02 char(200), C_NUCLEO_I char(14), D_NUCLEO_I char(80), _count_E00 char(200), CF_50K char(5),
      CF_5K char(5), HUSO char(20), OBJECTID long, _count_5K_ char(200), ENTIDAD char(250), FUENTE char(250), IDIOMA char(5), ORIENTACIO char(20), TAMANO char(20), CODINE1 char(20), CODINE2 char(20), ENCLAVE1 char(20), ENCLAVE2 char(20), ID_LINLIM char(43), MUN1 char(250), MUN2 char(250), URL_RESOUR char(250), _count_LIM char(200)
Inspector_2
Hidrografia_pun (reader GEODATABASE_FILE_1)
    attributes: objectid integer, ID_Fenomen char(254), ID_HOJA char(5), NOMBRE char(250), TIPO char(3)
    -> Hidrografia_pun (writer GEODATABASE_FILE_2)
    -> GeometryValidator
Hidrografia_pun (writer GEODATABASE_FILE_2)
    attributes: objectid integer, ID_Fenomen char(254), ID_HOJA char(5), NOMBRE char(250), TIPO char(3)
NomGeo_pun (reader GEODATABASE_FILE_1)
    attributes: objectid integer, ID_Fenomen char(5), CODIGO char(17), ENTIDAD char(250), FUENTE char(250), ID_HOJA char(5), IDIOMA char(3), NOMBRE char(250), ORIENTACION double, TAMANO double
    -> NomGeo_pun (writer GEODATABASE_FILE_2)
    -> GeometryValidator
NomGeo_pun (writer GEODATABASE_FILE_2)
    attributes: objectid integer, ID_Fenomen char(5), CODIGO char(17), ENTIDAD char(250), FUENTE char(250), ID_HOJA char(5), IDIOMA char(3), NOMBRE char(250), ORIENTACION double, TAMANO double
RedFerro_pun (reader GEODATABASE_FILE_1)
    attributes: objectid integer, ID_Fenomen char(5), EXTENSION char(20), FECHA_ALTA char(8), FUENTE char(40), ID_FERRO char(20), ID_PORPK char(20), ID_TRAMO char(20), ID_VIAL char(20), NUMERO double, ID_HOJA char(5)
    -> RedFerro_pun (writer GEODATABASE_FILE_2)
    -> GeometryValidator
RedFerro_pun (writer GEODATABASE_FILE_2)
    attributes: objectid integer, ID_Fenomen char(5), EXTENSION char(20), FECHA_ALTA char(8), FUENTE char(40), ID_FERRO char(20), ID_PORPK char(20), ID_TRAMO char(20), ID_VIAL char(20), NUMERO double, ID_HOJA char(5)
RedViaria_pun (reader GEODATABASE_FILE_1)
    attributes: objectid integer, ID_Fenomen char(5), EXTENSION char(20), FECHA_ALTA char(8), FUENTE char(40), ID_VIARIA char(20), ID_PORPK char(20), ID_TRAMO char(20), ID_VIAL char(20), NUMERO double, SENTIDO_PK char(3), TIPO_PORPK char(3), ID_HOJA char(5)
    -> RedViaria_pun (writer GEODATABASE_FILE_2)
    -> GeometryValidator
RedViaria_pun (writer GEODATABASE_FILE_2)
    attributes: objectid integer, ID_Fenomen char(5), EXTENSION char(20), FECHA_ALTA char(8), FUENTE char(40), ID char(20), ID_PORPK char(20), ID_TRAMO char(20), ID_VIAL char(20), NUMERO double, SENTIDO_PK char(3), TIPO_PORPK char(3)
Relieve_pun (reader GEODATABASE_FILE_1)
    attributes: objectid integer, ID_Fenomen char(5), ID_HOJA char(5), CONTEXTO char(3), COTA double, TIPO char(3)
    -> Relieve_pun (writer GEODATABASE_FILE_2)
    -> GeometryValidator
Relieve_pun (writer GEODATABASE_FILE_2)
    attributes: objectid integer, ID_Fenomen char(5), ID_HOJA char(5), CONTEXTO char(3), COTA double, TIPO char(3)
ServInst_pun (reader GEODATABASE_FILE_1)
    attributes: objectid integer, ID_Fenomen char(5), ID_HOJA char(5), NOMBRE char(250), TIPO char(3), CODEXPLOT char(50), ESTADO char(3), ENERGIA char(3)
    -> ServInst_pun (writer GEODATABASE_FILE_2)
    -> GeometryValidator
ServInst_pun (writer GEODATABASE_FILE_2)
    attributes: objectid integer, ID_Fenomen char(5), ID_HOJA char(5), NOMBRE char(250), TIPO char(3), CODEXPLOT char(50), ESTADO char(3), ENERGIA char(3)
PuntosGeodesicos_pun (reader GEODATABASE_FILE_1)
    attributes: OBJECTID integer, ID_Fenomen char(5), ASTRONOMIC char(8), FECHACALC char(8), GRAVEDAD char(3), H_ORTO float, ID_HOJA char(5), IDCALC char(10), IDENTIFICA char(10), NOMBRE char(254), ORGANISMOC char(250), REDGEODESI char(3), REDNIVELAC char(3), TITULAR char(3)
    -> PuntosGeodesicos_pun (writer GEODATABASE_FILE_2)
    -> GeometryValidator
PuntosGeodesicos_pun (writer GEODATABASE_FILE_2)
    attributes: OBJECTID integer, ID_Fenomen char(5), ASTRONOMIC char(8), FECHACALC char(8), GRAVEDAD char(3), H_ORTO float, ID_HOJA char(5), IDCALC char(10), IDENTIFICA char(10), NOMBRE char(254), ORGANISMOC char(250), REDGEODESI char(3), REDNIVELAC char(3), TITULAR char(3)
PuntosGNSS_pun (reader GEODATABASE_FILE_1)
    attributes: OBJECTID integer, ID_Fenomen char(5), COD_IERS char(9), ID_HOJA char(5), IDENTIFICA char(10), RDIS char(250), RED_EPN char(3), RTK char(3), TITULAR char(3)
    -> PuntosGNSS_pun (writer GEODATABASE_FILE_2)
    -> GeometryValidator
PuntosGNSS_pun (writer GEODATABASE_FILE_2)
    attributes: OBJECTID integer, ID_Fenomen char(5), COD_IERS char(9), ID_HOJA char(5), IDENTIFICA char(10), RDIS char(250), RED_EPN char(3), RTK char(3), TITULAR char(3)
EdiPobCons_pun (reader GEODATABASE_FILE_1)
    attributes: objectid integer, ID_Fenomen char(5), ID_HOJA char(5), NOMBRE char(250), TIPO char(3), VISTO char(3), BIC char(3), CLASIF char(3), ESTADO char(3), SITUACION char(3), USO char(3)
    -> EdiPobCons_pun (writer GEODATABASE_FILE_2)
    -> GeometryValidator
GeometryValidator
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]SELF_INTERSECTION_TOLERANCE]None]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme SURFACE_ORIENTATION  SOLID_ORIENTATION
    SUMMARY = Detailed
    ISSUE_LOCATIONS -> AttributeCreator_50
AttributeCreator_50
    ATTR_TABLE = SET_TO Err_REASON = ERROR_Deaggregate_LINE_POLYGON_POINT
    -> AttributeCreator_51
AttributeCreator_51
    ATTR_TABLE = SET_TO igds_level_name = @Value(Err_REASON)
    -> Level1 (writer DGNV8_3)
Level1 (writer DGNV8_3)
EdiPobCons_pun (writer GEODATABASE_FILE_2)
    attributes: objectid integer, ID_Fenomen char(5), ID_HOJA char(5), NOMBRE char(250), TIPO char(3), VISTO char(3), BIC char(3), CLASIF char(3), ESTADO char(3), SITUACION char(3), USO char(3)
GeometryFilter_17
    BREAK_AGG = No
    GEOM_PORT_NAMES = Point Line Area
    POINT -> Junction_21
    LINE -> Shapefile1 (writer ESRISHAPE_4)
    AREA -> Shapefile1 (writer ESRISHAPE_1)
    <UNFILTERED> -> Junction_21
GeometryFilter_18
    BREAK_AGG = No
    GEOM_PORT_NAMES = Point Line Area
    POINT -> Junction_21
    LINE -> Shapefile1 (writer ESRISHAPE_4)
    AREA -> Shapefile1 (writer ESRISHAPE_1)
    <UNFILTERED> -> Junction_21
Shapefile1 (writer ESRISHAPE_4)
Shapefile1 (writer ESRISHAPE_1)
    attributes: objectid_2 long, Error long, fme_featur long
Junction_21
