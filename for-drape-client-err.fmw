FME workspace for-drape-client-err.fmw

Parameters:
- SourceDataset_DGNV8 = H:\Exchange\Sunshine\439_After_Atmetri.dgn   # Source Bentley MicroStation Design File(s)
- FEATURE_TYPES = 1003_Axis_SING_carriageway_CNX_Use_Unclassified_ENL_Ln 1003_Axis_SING_Carriageway_ELE_Use_Trunk_Ln 1003_Axis_SING_Carriageway_VAD_Use_Trunk_Ln 1003_SING_Carriageway_ELE_Use_Trunk_Shp 1003_SING_Carriageway_GRD_Use_Trunk_Shp 1003_SING_Carriageway_VAD_Use_Trunk_Shp 2000_Urban_road_axis_CNX_Unclassified_Generic_Ln 2000_Urban_road_axis_ELE_Generic_Ln 2000_Urban_road_MNZ_Shp 3001_RD_Axis_Paved_ELE_Ln 3001_RD_Axis_UnPaved_ELE_Ln 3001_RD_Axis_UnPaved_Hidden_Ln 3001_RD_Axis_VAD_Paved_Ln 3001_RD_Axis_VAD_UnPaved_Ln 3001_RD_CNX_Paved_Generic_Ln 3001_RD_CNX_UnPaved_Generic_Ln 3001_RD_Linear_VAD_UnPaved_Ln 3001_RD_Paved_ELE_Shp 3001_RD_Paved_GRD_Shp 3001_RD_Paved_VAD_Shp 3001_RD_Unpaved_ELE_Shp 3001_RD_Unpaved_GRD_Shp 3001_RD_Unpaved_VAD_Shp 3002_Trackpath_CNX_Ln 3002_Trackpath_ELE_Ln 3002_Trackpath_VAD_Ln 04001_Urban_Nucleaus_BLOCKS_MNZ_Use_Shp 04005_Building_Courtyard_Use_Shp 04007_Sing_Build_SL_ABN_Monastery_Convent_Shp 04007_Sing_Build_SL_ABN_Tower_Shp 04007_Sing_Build_SL_EDGE_ABN_Monastery_Convent_Ln 04007_Sing_Build_SL_EDGE_ABN_Tower_Ln 04007_Sing_Build_SL_EDGE_Health_Center_Use_Ln 04007_Sing_Build_SL_EDGE_Use_Church_Ln 04007_Sing_Build_SL_EDGE_Use_CityHall_Ln 04007_Sing_Build_SL_EDGE_Use_Heritage_Ln 04007_Sing_Build_SL_Health_Center_Use_Shp 04007_Sing_Build_SL_Use_Church_Pnt 04007_Sing_Build_SL_Use_Church_Shp 04007_Sing_Build_SL_Use_CityHall_Pnt 04007_Sing_Build_SL_Use_CityHall_Shp 04007_Sing_Build_SL_Use_Heritage_Shp 04008_Element_Construct_Block_MNZ_Line_Use_Ln 04010_Urban_Nucleaus_Polygon_Shp 04011_Yard_Garden_Vegetation_Urban_trees_Shp 05001_Graveyard_Use_Shp 05001_Sports_SRVCS_use_Shp 05002_Mining_FCLTY_Mine_Use_Shp 05002_Mining_FCLTY_Quary_Use_Shp 05004_INDSTRL_SRVCS_Generic_Use_Shp 05006_EDUCATNL_SRVCS_Primary_School_Public_Shp 05007_Sports_Footbal_Shp 05007_Sports_Multipurpose_Shp 05007_Sports_Other_Shp 05007_Sports_Tennis_Shp 06002_ARTIFI_Canal_Channel_Grd_Use_Shp 06002_ARTIFI_IRRI_Ditch_CNX_Unclassified_Use_Ln 06002_ARTIFI_IRRI_Ditch_LINEAR_Hidden_Use_Ln 06004_Non_PER_CNX_Water_Unclassified_Ln 06004_PER_CNX_Water_Unclassified_Ln 06004_PER_WATER_Unclassified_Shp 06007_NON_PER_Lagoon_water_Shp 06007_PER_Lagoon_water_Shp 06007_Pond_Generic_Water_Shp 06007_Pond_Pool_Water_Shp 06007_Pond_Trough_Water_Shp 06007_Pond_WATER_Reservoir_Water_Shp 06007_Swim_Pool_Shp 06007_WATER_Reservoir_Shp 07005_CETN_Bridge_Use_Shp 07005_CETN_RD_Island_Use_Shp 07005_Ditch_roadside_CNX_Unclassified_Ln 07005_Ditch_roadside_Hidden_Ln 08002_Antenna_Radio_Pnt 08002_Antenna_Telephone_Pnt 08003_Enegy_Install_Infra_Power_plant_Solar_Shp 08003_Enegy_Install_Infra_Substation_Other_Shp 08003_Enegy_Install_Infra_Telecommunication_Measure_Shp 08003_Enegy_Install_Infra_Wind_Other_Shp 08005_Pipe_Duct_Linear_Surface_Lying_Ln 08006_Deposit_FCLTY_HydroCarbon_Surface_Shp 08006_Deposit_FCLTY_Other_Surface_Shp 08006_Deposit_FCLTY_Water_Surface_Shp 09002_Public_works_Hydro_Earth_DAM_Shp 09002_Public_works_Hydro_Prey_Shp 10001_Trans_Infra_FCLTY_Paved_esplanade_Shp 10001_Trans_Infra_FCLTY_Unpaved_esplanade_Shp 10002_Waste_Accumulation_EDGE_Other_Shp 11003_Waste_MNGNT_FCLTY_Sewage_Treatement_plant_Shp 12000_Separation_Use_0_Ln 12001_Firewall_Shp 12003_Arable_Crop_CUH_Shp 12003_Bare_ground_SUD_Shp 12003_Forest_Tree_ARB_Shp 12003_Garden_HUE_Shp 12003_Pasture_PAS_Shp 12003_Scrub_MAT_Shp 12003_Woody_Crop_CUL_Shp Crt_Poly_1003_SING_Carriageway_GRD_Use_Trunk_Shp Crt_Poly_2000_Urban_road_MNZ_Shp Crt_Poly_3001_RD_Paved_GRD_Shp Crt_Poly_3001_RD_Unpaved_GRD_Shp Crt_Poly_04005_Building_Courtyard_Use_Shp Crt_Poly_05001_Graveyard_Use_Shp Crt_Poly_05002_Mining_FCLTY_Mine_Use_Shp Crt_Poly_05007_Sports_Footbal_Shp Crt_Poly_05007_Sports_Multipurpose_Shp Crt_Poly_05007_Sports_Other_Shp Crt_Poly_05007_Sports_Tennis_Shp Crt_Poly_06002_ARTIFI_Canal_Channel_Grd_Use_Shp Crt_Poly_06004_PER_WATER_Unclassified_Shp Crt_Poly_06007_NON_PER_Lagoon_water_Shp Crt_Poly_06007_PER_Lagoon_water_Shp Crt_Poly_06007_Pond_Generic_Water_Shp Crt_Poly_06007_Pond_Pool_Water_Shp Crt_Poly_06007_Pond_Trough_Water_Shp Crt_Poly_06007_Pond_WATER_Reservoir_Water_Shp Crt_Poly_06007_Swim_Pool_Shp Crt_Poly_06007_WATER_Reservoir_Shp Crt_Poly_07005_CETN_RD_Island_Use_Shp Crt_Poly_08003_Enegy_Install_Infra_Power_plant_Solar_Shp Crt_Poly_08003_Enegy_Install_Infra_Substation_Other_Shp Crt_Poly_08003_Enegy_Install_Infra_Telecommunication_Measure_Shp Crt_Poly_08003_Enegy_Install_Infra_Wind_Other_Shp Crt_Poly_08006_Deposit_FCLTY_HydroCarbon_Surface_Shp Crt_Poly_08006_Deposit_FCLTY_Other_Surface_Shp Crt_Poly_08006_Deposit_FCLTY_Water_Surface_Shp Crt_Poly_09002_Public_works_Hydro_Earth_DAM_Shp Crt_Poly_09002_Public_works_Hydro_Prey_Shp Crt_Poly_10001_Trans_Infra_FCLTY_Paved_esplanade_Shp Crt_Poly_10001_Trans_Infra_FCLTY_Unpaved_esplanade_Shp Crt_Poly_10002_Waste_Accumulation_EDGE_Other_Shp Crt_Poly_12001_Firewall_Shp Crt_Poly_12003_Arable_Crop_CUH_Shp Crt_Poly_12003_Bare_ground_SUD_Shp Crt_Poly_12003_Forest_Tree_ARB_Shp Crt_Poly_12003_Garden_HUE_Shp Crt_Poly_12003_Pasture_PAS_Shp Crt_Poly_12003_Scrub_MAT_Shp Crt_Poly_12003_Woody_Crop_CUL_Shp Crt_Poly_REF_12003_Arable_Crop_CUH_TXT Crt_Poly_REF_12003_Bare_ground_SUD_TXT Crt_Poly_REF_12003_Forest_Tree_ARB_TXT Crt_Poly_REF_12003_Meadow_PRD_TXT Crt_Poly_REF_12003_Pasture_PAS_TXT Crt_Poly_REF_12003_Rocky_ROQ_TXT Crt_Poly_REF_12003_Scrub_MAT_TXT Crt_Poly_REF_12003_Woody_Crop_CUL_TXT Default FME_Created_PNT_04005_Building_Building_ABN_Shp FME_Created_PNT_04005_Building_Building_Use_Shp FME_Created_PNT_04005_Building_Courtyard_Use_Shp FME_Created_PNT_04005_Building_Greenhouse_Use_Shp FME_Created_PNT_04005_Building_Industrial_Building_Use_Shp FME_Created_PNT_04005_Building_Light_building_Shed_Use_Shp FME_Created_PNT_04005_Building_Marquee_Use_Shp FME_Created_PNT_04005_Building_Niche_Use_Shp FME_Created_PNT_04005_Building_Transformer_Use_Shp FME_Created_PNT_04007_Sing_BUILD_USE_Pnt FME_Created_Poly_04005_Building_Building_ABN_Shp FME_Created_Poly_04005_Building_Building_Use_Shp FME_Created_Poly_04005_Building_Courtyard_Use_Shp FME_Created_Poly_04005_Building_Greenhouse_Use_Shp FME_Created_Poly_04005_Building_Industrial_Building_Use_Shp FME_Created_Poly_04005_Building_Light_building_Shed_Use_Shp FME_Created_Poly_04005_Building_Marquee_Use_Shp FME_Created_Poly_04005_Building_Niche_Use_Shp FME_Created_Poly_04005_Building_Transformer_Use_Shp FME_Created_Poly_04007_Sing_BUILD_USE_Pnt REF_1003_Axis_SING_Carriageway_GRD_Use_Trunk_Ln REF_1003_EDGE_SING_carriageway_GRD_Use_Trunk_Ln REF_2000_Urban_road_axis_GRD_Generic_Ln REF_3001_RD_Axis_Paved_GRD_Ln REF_3001_RD_Axis_UnPaved_GRD_Ln REF_3001_RD_EDGE_Paved_GRD_Ln REF_3001_RD_EDGE_UnPaved_GRD_Ln REF_3001_RD_Linear_Paved_GRD_Ln REF_3001_RD_Linear_UnPaved_GRD_Ln REF_03002_Depression_Contour_Ln REF_03002_Master_Contour_Ln REF_03002_Normal_Contour_Ln REF_3002_Trackpath_GRD_Ln REF_03003_Elev_Depression_Terrain_Pnt REF_03003_Elev_Elevated_Construction_Pnt REF_03003_Elev_Hill_Top_Pnt REF_03003_Elev_Terrain_Generic_Pnt REF_03003_Elev_Terrain_Top_Pnt REF_03003_Sleep_Head_Ln REF_03003_Slope_foot_cutting_Ln REF_03003_Slope_foot_embankment_Ln REF_03003_Slope_Head_cutting_Ln REF_03003_Slope_head_embankment_Ln REF_03003_Terrace_Margin_Ln REF_04003_Hedge_Ln REF_04003_Retaining_wall_Ln REF_04003_Wall_Ln REF_04003_Wire_fence_Ln REF_04005_Building_EDGE_Building_ABN_Ln REF_04005_Building_EDGE_Building_Use_Ln REF_04005_Building_EDGE_Courtyard_Use_Ln REF_04005_Building_EDGE_Greenhouse_Use_Ln REF_04005_Building_EDGE_Industrial_Building_Use_Ln REF_04005_Building_EDGE_Light_building_Shed_Use_Ln REF_04005_Building_EDGE_Marquee_Use_Ln REF_04005_Building_EDGE_Niche_Use_Ln REF_04005_Building_EDGE_Transformer_Use_Ln REF_04007_BOR_Singular_Building_USO_Ln REF_04008_Element_Construct_Curb_Use_Ln REF_04008_Element_Construct_Metallic_structure_Use_Ln REF_04011_Yard_Garden_Vegetation_Urban_trees_TXT REF_05001_Graveyard_EDGE_Use_Ln REF_05002_Mining_FCLTY_Mine_EDGE_Use_Ln REF_05007_Sports_EDGE_Footbal_Ln REF_05007_Sports_EDGE_Multipurpose_Ln REF_05007_Sports_EDGE_Other_Ln REF_05007_Sports_EDGE_Paintlines-Field_Ln REF_05007_Sports_EDGE_Tennis_Ln REF_06002_ARTIFI_Channel_AXIS_GRD_Use_Ln REF_06002_ARTIFI_Channel_EDGE_GRD_Use_Ln REF_06002_ARTIFI_IRRI_Ditch_LINEAR_GRD_Use_Ln REF_06004_NATUR_NON_PER_AXIS_Water_Unclassified_Ln REF_06004_NATUR_NON_PER_LINEAR_Water_Unclassified_Ln REF_06004_NATUR_PER_AXIS_Water_Unclassified_Ln REF_06004_NATUR_PER_EDGE_Water_Unclassified_Ln REF_06004_NATUR_PER_LINEAR_Water_Unclassified_Ln REF_06004_PER_EDGE_Water_Unclassified_Ln REF_06006_Coronation_line_Ln REF_06007_EDGE_Swimming_Pool_Ln REF_06007_NON_PER_Lagoon_EDGE_Water_Ln REF_06007_PER_Lagoon_EDGE_Water_Ln REF_06007_Pond_Generic_EDGE_Water_Ln REF_06007_Pond_Pool_EDGE_water_Ln REF_06007_Pond_Trough_EDGE_water_Ln REF_06007_Pond_Water_Reservoir_EDGE_Water_Ln REF_06007_Water_Reservoir_Edge_Ln REF_06008_Fountain_Pnt REF_07005_CETN_EDGE_RD_Island_Use_Ln REF_07005_Ditch_roadside_GRD_Ln REF_07005_Schema_Line_Bridge_Use_Ln REF_07005_Tajea_factory_work_Culvert_Ln REF_08001_Wind_turbine_Pnt REF_08003_Enegy_Install_Infra_Laying_Tower_Ln REF_08005_Pipe_Duct_Linear_Surface_Conveyer_belt_Ln REF_08006_Deposit_FCLTY_EDGE_HydroCarbon_Surface_Ln REF_08006_Deposit_FCLTY_EDGE_Other_Surface_Ln REF_08006_Deposit_FCLTY_EDGE_Water_Surface_Ln REF_09001_Catchment_Well_Pnt REF_09002_Public_works_Hydro_EDGE_Earth_DAM_Tie_Ln REF_09002_Public_works_Hydro_EDGE_Prey_OBR_Ln REF_09002_Public_works_Hydro_Linear_Prey_OBR_Ln REF_10001_Trans_Infra_FCLTY_EDGE_Paved_Esplanade_Ln REF_10001_Trans_Infra_FCLTY_EDGE_Unpaved_Esplanade_Ln REF_12000_Boundary_0_Ln REF_12000_Firewall_Axis_Ln REF_12000_Separation_Use_0_Ln REF_12000L_Firewall_Border_Ln REF_12003_Arable_Crop_CUH_TXT REF_12003_Bare_ground_SUD_TXT REF_12003_Forest_Tree_ARB_TXT REF_12003_Meadow_PRD_TXT REF_12003_Pasture_PAS_TXT REF_12003_Rocky_ROQ_TXT REF_12003_Scrub_MAT_TXT REF_12003_Woody_Crop_CUL_TXT
- SourceDataset_DGNV8_3 = H:\Exchange\Sunshine\Errores_shp_Conecti.dgn   # Source Bentley MicroStation Design File(s)
- FEATURE_TYPES_2 = Default Errores_shp_Conecti_CubiertaTer_pol Errores_shp_Conecti_EdiPobCons_lin Errores_shp_Conecti_RedViaria_lin Errores_shp_Conecti_ServInst_pol
- SourceDataset_XLSXR = H:\Exchange\manv\FME_DRAPE_GROUND_COTA_ERROR_RULES_Ver-02.xlsx   # Source Microsoft Excel File(s)
- FEATURE_TYPES_3 = FME_DRAPE_GROUND_LIST
- DestDataset_DGNV8 = H:\Exchange\manv\Drpae_NEW\DRaped_NEW-connec.dgn   # Destination Bentley MicroStation Design File

Readers:
- DGNV8_1: DGNV8 from $(SourceDataset_DGNV8)
- DGNV8_2: DGNV8 from $(SourceDataset_DGNV8_3)
- XLSXR_1: XLSXR from $(SourceDataset_XLSXR)

Writers:
- DGNV8_3: DGNV8 to $(DestDataset_DGNV8)

05007_Sports_Footbal_Shp (reader DGNV8_1)
    -> Counter
Counter
    CNT_ATTR = _count
    DOMAIN = counter
    SCOPE = Global
    START = 0
    -> FeatureJoiner [LEFT]
FME_DRAPE_GROUND_LIST (reader XLSXR_1)
    attributes: Level_Name char(62), Is_Ground_Object char(4)
    -> FeatureJoiner [RIGHT]
FeatureJoiner
    ATTR_CONFLICT_RES = Prefer Left
    GEOMETRY_HANDLING = Prefer Left
    JOIN_KEYS = igds_level_name Level_Name AUTO
    JOIN_MODE = Full
    JOINED -> Tester
Tester
    BOOL_OP = OR
    TEST_CLAUSE:
      TEST @Value(Is_Ground_Object) = Yes
      TEST @Value(Is_Ground_Object) = yes
    TEST_MODE = TEST
    PASSED -> GeometryFilter
GeometryFilter
    FILTER_MODE = SIMPLE
    FILTER_MULTI = FILTER_TYPES]"Point Text Line Area Surface"]FME_CONTROLLER_QUERY_FILE]]FME_CONTROLLER_CHOICE]Simple
    <UNFILTERED> -> SurfaceDraper [BREAKLINES]
    Point -> SurfaceDraper [POINTS/LINES]
    Text -> GeometryCoercer
    Curve -> SurfaceDraper [BREAKLINES]
    Area -> GeometryCoercer_2
GeometryCoercer_2
    GQUERY:
      for $geom in //geometry
      where $geom/count(parent::geometry) = 0
      return number($geom/@fme_id)
    KIND = fme_line
    COERCED -> SurfaceDraper [BREAKLINES]
GeometryCoercer
    GQUERY:
      for $geom in //geometry
      where $geom/count(parent::geometry) = 0
      return number($geom/@fme_id)
    KIND = fme_point
    COERCED -> SurfaceDraper [POINTS/LINES]
Errores_shp_Cotas_CubiertaTer (reader DGNV8_2)
    -> GeometryFilter_2
GeometryFilter_2
    FILTER_MODE = SIMPLE
    FILTER_MULTI = FILTER_TYPES]"Point Text Line Area Surface"]FME_CONTROLLER_QUERY_FILE]]FME_CONTROLLER_CHOICE]Simple
    Point -> CoordinateExtractor
CoordinateExtractor
    IND = 0
    MODE = Specify Coordinate
    X_ATTR = _x_OLD
    Y_ATTR = _y_OLD
    Z_ATTR = _z_OLD
    -> GeometryCoercer_3
GeometryCoercer_3
    GQUERY:
      for $geom in //geometry
      where $geom/count(parent::geometry) = 0
      return number($geom/@fme_id)
    KIND = fme_point
    COERCED -> SurfaceDraper [DRAPE_FEATURES]
SurfaceDraper
    ADDZ_TYPE = Replace Z
    DRAPE_TYPE = VERTEX
    INTERPOLATION_TYPE = AUTO
    TOLERANCE = 0.1
    DRAPED_FEATURES -> CoordinateExtractor_2
CoordinateExtractor_2
    IND = 0
    MODE = Specify Coordinate
    X_ATTR = _x_NEW
    Y_ATTR = _y_NEW
    Z_ATTR = _z_NEW
    -> AttributeCreator
AttributeCreator
    ATTR_TABLE = SET_TO DIfference = @Evaluate(@Value(_z_NEW)-@Value(_z_OLD))
    -> Tester_2
Tester_2
    BOOL_OP = OR
    TEST_CLAUSE = NUM_TEST @Value(DIfference) RANGE [-5,5]
    TEST_MODE = NUM_TEST
    PASSED -> AttributeCreator_2
    FAILED -> AttributeCreator_3
AttributeCreator_2
    ATTR_TABLE = SET_TO igds_level_name = @Value(igds_level_name)_Error_Difference-less_than_5_Meter
    -> Errores_shp_Cotas_CubiertaTer (writer DGNV8_3)
AttributeCreator_3
    ATTR_TABLE = SET_TO igds_level_name = @Value(igds_level_name)_Error_Manual_Check_5_Mts_Above
    -> Errores_shp_Cotas_CubiertaTer (writer DGNV8_3)
Errores_shp_Cotas_CubiertaTer (writer DGNV8_3)
