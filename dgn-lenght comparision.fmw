FME workspace dgn-lenght comparision.fmw

Parameters:
- SourceDataset_DGNV8 = C:\Projects-3D\OMNR_2021\Lidar_data_analysis\01-feb-2022\3F_P2_WaterVector.dgn   # Source Bentley MicroStation Design File(s)
- FEATURE_TYPES = Island Lake River Island_inside_Lake
- SourceDataset_DGNV8_3 = C:\Projects-3D\OMNR_2021\Lidar_data_analysis\01-feb-2022\3F_Part_02_Water_Final.dgn   # Source Bentley MicroStation Design File(s)
- FEATURE_TYPES_2 = Z_Accuracy_XY_Lake Z_Accuracy_XY_River Z_Accuracy (XY)_River Z_Accuracy_XY_Island Z_Missing_Lake

Readers:
- DGNV8_1: DGNV8 from $(SourceDataset_DGNV8)
- DGNV8_2: DGNV8 from $(SourceDataset_DGNV8_3)

Lake (reader DGNV8_1)
    -> GeometryCoercer
GeometryCoercer
    GQUERY:
      for $geom in //geometry
      where $geom/count(parent::geometry) = 0
      return number($geom/@fme_id)
    KIND = fme_line
    COERCED -> LengthCalculator
LengthCalculator
    DIM = 2
    LEN_ATTR = _length_Vector_Final
    MULT = 1
    -> AttributeRounder_2
AttributeRounder_2
    PLACES = 2
    ROUND_TYPE = Nearest
    SRC_ATTRS = _length_Vector_Final
    -> StatisticsCalculator
StatisticsCalculator
    CALCULATION_MODE = NUMERIC
    FEAT_STATS = _length_Vector_Final,NUMERIC_MODE,,,,SUM,,,,,,,,
    SUMMARY -> AttributeCreator
Island_Adjust (reader DGNV8_2)
    -> GeometryCoercer_2
GeometryCoercer_2
    GQUERY:
      for $geom in //geometry
      where $geom/count(parent::geometry) = 0
      return number($geom/@fme_id)
    KIND = fme_line
    COERCED -> LengthCalculator_2
LengthCalculator_2
    DIM = 2
    LEN_ATTR = _length_Lidar_modified
    MULT = 1
    -> AttributeRounder
AttributeRounder
    PLACES = 2
    ROUND_TYPE = Nearest
    SRC_ATTRS = _length_Lidar_modified
    -> StatisticsCalculator_2
StatisticsCalculator_2
    CALCULATION_MODE = NUMERIC
    FEAT_STATS = _length_Lidar_modified,NUMERIC_MODE,,,,SUM,,,,,,,,
    SUMMARY -> AttributeCreator
AttributeCreator
    ATTR_TABLE:
      SET_TO _length_Lidar_modified.sum
      SET_TO _length_Vector_Final.sum
      SET_TO % of modified data = @div(@Value(_length_Lidar_modified.sum),@Value(_length_Vector_Final.sum))
    -> AttributeCreator_2
AttributeCreator_2
    ATTR_TABLE = SET_TO % or modified data = @div(@Value(_length_Lidar_modified.sum),@Value(_length_Vector_Final.sum))
