FME workspace Vector_LengthCalculator_filewise.fmw

Parameters:
- SourceDataset_DGNV8 = ""D:\05_Test\omnr\From_delivery\Block_2B.dgn" "D:\05_Test\omnr\From_delivery\Block_3E.dgn" "D:\05_Test\omnr\From_delivery\Block_5C_North.dgn" "D:\05_Test\omnr\From_delivery\Block_5F.dgn" "D:\05_Test\omnr\From_delivery\Block_5G.dgn" "D:\05_Test\omnr\From_delivery\Block_5H.dgn" "D:\05_Test\omnr\From_delivery\Block_5I.dgn" "D:\05_Test\omnr\From_delivery\Block_5L.dgn" "D:\05_Test\omnr\From_delivery\Block_5M.dgn" "D:\05_Test\omnr\From_delivery\Block_6G.dgn" "D:\05_Test\omnr\From_delivery\Block_6K.dgn" "D:\05_Test\omnr\From_delivery\Block_6N_North.dgn" "D:\05_Test\omnr\From_delivery\Block_6N_South.dgn" "D:\05_Test\omnr\From_delivery\Block_6O.dgn" "D:\05_Test\omnr\From_delivery\Block5C_Central.dgn" "D:\05_Test\omnr\From_delivery\Block5C_South.dgn" "D:\05_Test\omnr\From_delivery\Block5D.dgn" "D:\05_Test\omnr\From_delivery\Block5E.dgn" "D:\05_Test\omnr\From_delivery\Block5K.dgn" "D:\05_Test\omnr\From_delivery\Block6C.dgn" "D:\05_Test\omnr\From_delivery\Block6E.dgn""   # Source Bentley MicroStation Design File(s)
- FEATURE_TYPES = Island Island_inside_Lake Island_inside_lsland Water
- DestDataset_XLSXW = D:\05_Test\omnr\From_delivery\OMNR_Vector_LenghtCalculator.xlsx   # Destination Microsoft Excel File

Readers:
- DGNV8_1: DGNV8 from $(SourceDataset_DGNV8)

Writers:
- XLSXW_1: XLSXW to $(DestDataset_XLSXW)

Default (reader DGNV8_1)
    -> GeometryCoercer
GeometryCoercer
    GQUERY:
      for $geom in //geometry
      where $geom/count(parent::geometry) = 0
      return number($geom/@fme_id)
    KIND = fme_line
    COERCED -> Counter
Counter
    CNT_ATTR = _count
    GROUP_BY = igds_basename
    SCOPE = Local
    START = 1
    -> LengthCalculator
LengthCalculator
    DIM = 2
    LEN_ATTR = _length
    MULT = 1
    -> StatisticsCalculator
StatisticsCalculator
    CALCULATION_MODE = NUMERIC
    FEAT_STATS = fme_feature_type,NUMERIC_MODE,,,COUNT,,,,,,,,,,;_length,NUMERIC_MODE,,,,SUM,,,,,,,,,
    GROUP_BY = igds_basename
    SUMMARY -> AttributeManager
AttributeManager
    ATTR_TABLE:
      RENAME_SET_VALUE igds_basename > FileNames (varchar(50))
      RENAME_SET_VALUE fme_feature_type.total_count > FeaturesTotalCount (uint64)
      RENAME_SET_VALUE _length.sum > FeaturesTotalLength (real64)
    -> Sheet1 (writer XLSXW_1)
Sheet1 (writer XLSXW_1)
    attributes: FileNames string(50), FeaturesTotalCount number(50), FeaturesTotalLength number(50)
