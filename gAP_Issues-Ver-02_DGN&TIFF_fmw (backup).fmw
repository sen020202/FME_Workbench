FME workspace gAP_Issues-Ver-02_DGN&TIFF_fmw (backup).fmw

Parameters:
- SourceDataset_DGNV8 = $(FME_MF_DIR)Test-02.dgn   # Source Bentley MicroStation Design File(s)
- FEATURE_TYPES = 4I_Tiles_Delivered Island Water
- SourceDataset_GEOTIFF = ""$(FME_MF_DIR)1kmZ173790520302021L.tif" "$(FME_MF_DIR)1kmZ173790520402021L.tif" "$(FME_MF_DIR)1kmZ173790520502021L.tif" "$(FME_MF_DIR)1kmZ173790520602021L.tif" "$(FME_MF_DIR)1kmZ173790520702021L.tif" "$(FME_MF_DIR)1kmZ173800520302021L.tif" "$(FME_MF_DIR)1kmZ173800520402021L.tif" "$(FME_MF_DIR)1kmZ173800520502021L.tif" "$(FME_MF_DIR)1kmZ173800520602021L.tif" "$(FME_MF_DIR)1kmZ173800520702021L.tif" "$(FME_MF_DIR)1kmZ173810520302021L.tif" "$(FME_MF_DIR)1kmZ173810520402021L.tif" "$(FME_MF_DIR)1kmZ173810520502021L.tif" "$(FME_MF_DIR)1kmZ173810520602021L.tif" "$(FME_MF_DIR)1kmZ173810520702021L.tif""   # Source GeoTIFF File(s)
- FEATURE_TYPES_2 = GEOTIFF

Readers:
- DGNV8_1: DGNV8 from $(SourceDataset_DGNV8)
- GEOTIFF_1: GEOTIFF from $(SourceDataset_GEOTIFF)

4I_Tiles_Delivered (reader DGNV8_1)
    -> AttributeFilter
AttributeFilter
    ATTR_NAME = igds_level_name
    ATTR_VALUES = <Empty>,<Missing>,<Null>,<Unfiltered>,Water,Island,4I_Tiles_Delivered
    Water -> Junction
    Island -> Junction
    4I_Tiles_Delivered -> GeometryFilter
GeometryFilter
    BREAK_AGG = No
    GEOM_PORT_NAMES = Area Text
    AREA -> SpatialFilter [Candidate]
    TEXT -> SpatialFilter [Filter]
SpatialFilter
    AGGREGATE_HANDLING = Yes
    ATTR_ACCUM_MODE = Prefix Filter
    ATTR_PREFIX = _T_
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager
    FAILED -> AttributeCreator_5
AttributeManager
    ATTR_TABLE:
      REMOVE _T_fme_feature_type
      RENAME_SET_VALUE _T_fme_text_string > Tile_Name
      REMOVE _T_fme_rotation
      REMOVE _T_fme_text_size
      REMOVE fme_feature_type
      REMOVE fme_basename
      REMOVE fme_text_string
      REMOVE igds_element_id
      REMOVE igds_level
      REMOVE igds_level_name
      REMOVE igds_text_string{}
      REMOVE _predicate
    -> CoordinateExtractor_2
CoordinateExtractor_2
    LIST_NAME = _indices
    MODE = All Coordinates
    -> ListConcatenator
ListConcatenator
    DROP_EMPTY_PARTS = No
    LIST_ATTR = _indices{}.x
    SEP = ,
    VAL_ATTR = X_concatenated
    -> ListConcatenator_2
ListConcatenator_2
    DROP_EMPTY_PARTS = No
    LIST_ATTR = _indices{}.y
    SEP = ,
    VAL_ATTR = Y_concatenated
    -> FeatureJoiner [RIGHT]
AttributeCreator_5
    ATTR_TABLE:
      SET_TO igds_level_name = Err_Input_AOI_DGN_NO_TXT
      SET_TO igds_level = Err_Input_AOI_DGN_NO_TXT
Junction
    -> Clipper [CLIPPEE]
GEOTIFF (reader GEOTIFF_1)
    -> BoundingBoxReplacer
BoundingBoxReplacer
    BOXTYPE = 2D Oriented Bounding Box
    BOX -> AreaCalculator
AreaCalculator
    AREA_ATTR = _area
    AREA_TYPE = Plane Area
    MULT = 1
    -> Tester_3
Tester_3
    BOOL_OP = OR
    COMPOSITE_TEST = 1
    TEST_CLAUSE = TEST @Value(_area) = 1000000
    TEST_MODE = TEST
    PASSED -> CoordinateExtractor
    PASSED -> Dissolver
    FAILED -> AttributeCreator_2
CoordinateExtractor
    LIST_NAME = _indices
    MODE = All Coordinates
    -> AttributeCreator
AttributeCreator
    ATTR_TABLE = SET_TO Tile_Name = @Value(fme_basename)
    -> ListConcatenator_3
ListConcatenator_3
    DROP_EMPTY_PARTS = No
    LIST_ATTR = _indices{}.x
    SEP = ,
    VAL_ATTR = GTX_concatenated
    -> ListConcatenator_4
ListConcatenator_4
    DROP_EMPTY_PARTS = No
    LIST_ATTR = _indices{}.y
    SEP = ,
    VAL_ATTR = GTY_concatenated
    -> FeatureJoiner [LEFT]
FeatureJoiner
    ATTR_CONFLICT_RES = Use Left
    GEOMETRY_HANDLING = Use Left
    GROUP_BY = Tile_Name
    JOIN_KEYS = GTX_concatenated X_concatenated AUTO
    JOIN_MODE = Full
    JOINED -> Tester
Tester
    BOOL_OP = AND
    COMPOSITE_TEST = 1 AND 2
    TEST_CLAUSE:
      TEST @Value(GTX_concatenated) = @Value(X_concatenated)
      TEST @Value(GTY_concatenated) = @Value(Y_concatenated)
    TEST_MODE = TEST
    FAILED -> AttributeCreator_4
AttributeCreator_4
    ATTR_TABLE:
      SET_TO igds_level_name = Err_GAP_Issues
      SET_TO igds_level = Err_GAP_Issues
    -> Errors
AttributeCreator_2
    ATTR_TABLE:
      SET_TO igds_level_name = Err_Less_Tile_Size
      SET_TO igds_level = Err_Less_Tile_Size
    -> Errors
Dissolver
    ACCUM_INPUT_ATTRS = Use Attributes From One Feature
    CLEANING_TOLERANCE = Automatic
    CONNECT_Z_MODE = First Wins
    DEAGGREGATE_INPUT = Yes
    AREA -> Bufferer
    AREA -> GeometryCoercer
Bufferer
    ANGLE = 22.5
    CAP_STYLE = Arc
    CORNER_STYLE = Arc
    MODE = AREA
    OFFSET = -0.5
    OFFSET_UNITS = NONE
    PRECISION = APPROX
    BUFFERED -> Clipper [CLIPPER]
Clipper
    BOUNDARY_CASES = Treat as Inside
    CLEANING_TOLERANCE = None
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    OUTSIDE -> GeometryCoercer_2
GeometryCoercer_2
    GQUERY:
      for $geom in //geometry
      where $geom/count(parent::geometry) = 0
      return number($geom/@fme_id)
    KIND = fme_line
    COERCED -> LineOnLineOverlayer [LINE]
GeometryCoercer
    GQUERY:
      for $geom in //geometry
      where $geom/count(parent::geometry) = 0
      return number($geom/@fme_id)
    KIND = fme_line
    COERCED -> LineOnLineOverlayer [LINE]
LineOnLineOverlayer
    ATTRS_ACCUM_MODE = Merge Attributes
    CLEANING_TOLERANCE = None
    DEAGGREGATE_INPUT = Yes
    GENERATE_LIST_DROP = NO
    OV_ATTR = L_Overlaps
    SEPARATE_COLLINEAR_SEGMENTS = No
    LINE -> Tester_2
Tester_2
    BOOL_OP = OR
    COMPOSITE_TEST = 1 OR 2
    TEST_CLAUSE:
      TEST @Value(igds_level_name) = Water
      TEST @Value(igds_level_name) = Island
    TEST_MODE = TEST
    PASSED -> Tester_4
Tester_4
    BOOL_OP = OR
    COMPOSITE_TEST = 1
    TEST_CLAUSE = TEST @Value(L_Overlaps) = 1
    TEST_MODE = TEST
    FAILED -> AttributeCreator_3
AttributeCreator_3
    ATTR_TABLE:
      SET_TO igds_level_name = Check_Vector_Not_Compiled_Till_AOI
      SET_TO igds_level = Check_Vector_Not_Compiled_Till_AOI
    -> Errors
Errors: Inspector
