FME workspace _DGN_LEVELS_Validation.fmw

Parameters:
- DestDataset_DGNV8 =
- FEATURE_TYPES =
- SourceDataset_DGNV8 =

Readers:
- DGNV8_1: DGNV8 from $(SourceDataset_DGNV8)

Writers:
- DGNV8_2: DGNV8 to $(DestDataset_DGNV8)

Contour (reader DGNV8_1)
    -> Counter
Counter
    CNT_ATTR = ID
    DOMAIN = counter
    SCOPE = Global
    START = 1
    -> AttributeFilter
AttributeFilter
    ATTR_NAME = igds_level_name
    ATTR_VALUES = <Empty>,<Missing>,<Null>,<Unfiltered>,Water,Island,Contour,Island_Inside_Island,Island_Inside_Lake
    Water -> SpatialFilter [Filter]
    Water -> Clipper [CLIPPER]
    Water -> Counter_2
    Island -> SpatialFilter [Candidate]
    Island -> Counter_3
    Island -> Clipper_2 [CLIPPER]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    FAILED -> Err_Island_Without_Water
    FAILED -> AttributeCreator
AttributeCreator
    ATTR_TABLE:
      SET_TO igds_level_name = Err_Island_Without_Water
      SET_TO igds_level = Err_Island_Without_Water
    -> DGNStyler
DGNStyler
    COLOR_BY_LEVEL_DISPLAY = No
    COLOR_CHOICE_DISPLAY = RGB
    LINE_STYLE = 0
    LINE_WEIGHT = 3
    RGB_COLOR = 1,0,0
    DGNStyled -> Junction
Err_Island_Without_Water: Inspector
Counter_2
    CNT_ATTR = _TID
    DOMAIN = counter
    SCOPE = Global
    START = 1
    -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Tester
Tester
    BOOL_OP = OR
    COMPOSITE_TEST = 1
    TEST_CLAUSE = TEST @Value(_clipped) = yes
    TEST_MODE = TEST
    PASSED -> Err_Water_Inside_Water
    PASSED -> AttributeCreator_2
AttributeCreator_2
    ATTR_TABLE:
      SET_TO igds_level_name = Err_Water_Inside_Water
      SET_TO igds_level = Err_Water_Inside_Water
    -> DGNStyler_2
DGNStyler_2
    COLOR_BY_LEVEL_DISPLAY = No
    COLOR_CHOICE_DISPLAY = RGB
    LINE_STYLE = 0
    LINE_WEIGHT = 3
    RGB_COLOR = 1,0,0
    DGNStyled -> Junction
Err_Water_Inside_Water: Inspector
Counter_3
    CNT_ATTR = _TID
    DOMAIN = counter
    SCOPE = Global
    START = 1
    -> Clipper_2 [CLIPPEE]
Clipper_2
    ATTR_ACCUM_MODE = Prefix Clipper
    BOUNDARY_CASES = Treat as Inside
    CLEANING_TOLERANCE = Automatic
    CLIPPED_ATTR = _clipped
    CLIPPER_PREFIX = _W_
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Tester_2
Tester_2
    BOOL_OP = OR
    COMPOSITE_TEST = 1
    TEST_CLAUSE = TEST @Value(_clipped) = yes
    TEST_MODE = TEST
    PASSED -> Err_Island_Inside_Island
    PASSED -> AttributeCreator_3
    FAILED -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    POLY_DIRECTION = _direction
    POLY_LIST_ATTRS_TO_INCLUDE_MODE = All Attributes
    POLY_LIST_NAME = _N_
    SNAPTYPE_PARAM = None
    AREA -> ListExploder
ListExploder
    ATTR_ACCUM_MODE = Merge List Attributes
    ATTR_CONFLICT_RES = Use List Attribute Values
    INDEX_ATTR = _element_index
    LIST_ATTR = _N_{}
    ELEMENTS -> Tester_3
Tester_3
    BOOL_OP = OR
    COMPOSITE_TEST = 1
    TEST_CLAUSE = TEST @Value(_element_index) = 0
    TEST_MODE = TEST
    FAILED -> Err_Island_Inside_Island
    FAILED -> AttributeCreator_3
AttributeCreator_3
    ATTR_TABLE:
      SET_TO igds_level_name = Err_Island_Inside_Island
      SET_TO igds_level = Err_Island_Inside_Island
    -> DGNStyler_3
DGNStyler_3
    COLOR_BY_LEVEL_DISPLAY = No
    COLOR_CHOICE_DISPLAY = RGB
    LINE_STYLE = 0
    LINE_WEIGHT = 3
    RGB_COLOR = 1,0,0
    DGNStyled -> Junction
Junction
    -> AttributeCreator_4
AttributeCreator_4
    ATTR_TABLE = SET_TO New_Name = @Value(fme_basename)_DGN_LVL_Err
    -> Contour (writer DGNV8_2)
Contour (writer DGNV8_2)
Err_Island_Inside_Island: Inspector
