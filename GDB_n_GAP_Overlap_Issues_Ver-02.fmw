FME workspace GDB_n_GAP_Overlap_Issues_Ver-02.fmw

Parameters:
- SourceDataset_DGNV8_2 = $(FME_MF_DIR)Belaka_Mbere_3b1_Vegetation.dgn   # Source Bentley MicroStation Design File(s)
- DestDataset_DGNV8 = $(FME_MF_DIR)GSINT_ERROR_GAP_OVERLAP.dgn   # Destination Bentley MicroStation Design File
- FEATURE_TYPES = Default Hydro_Lake Surface Hydro_Surface Permanent Vegetation_Bare Soil Vegetation_Cultivation area without trees Vegetation_Galery Forest Vegetation_Light Forest Vegetation_Rice field Vegetation_Shrub Savanna Vegetation_Tree Savanna AOI
- SEED_FILE_DGNV8 = C:\Program Files\FME/design/seed3d_m_v8.dgn   # Seed File (V8 only)
- CELL_LIBRARY_DGNV8 = C:\Program Files\FME/design/default_v8.cel   # Cell Library File

Readers:
- DGNV8_1: DGNV8 from $(SourceDataset_DGNV8_2)

Writers:
- DGNV8_2: DGNV8 to $(DestDataset_DGNV8)

Vegetation_Grassland Savanna (reader DGNV8_1)
    -> AttributeExposer_2
AttributeExposer_2
    ATTR_LIST = igds_level,igds_level_name
    -> AttributeFilter
AttributeFilter
    ATTR_NAME = igds_level_name
    ATTR_VALUES = <Empty>,<Missing>,<Null>,<Unfiltered>,AOI,Building_Polygon,Building_Urban_built_up_area,Hydro_Surface Permanent,Hydro_Surface Temporary,Vegetation_Bare Soil,Vegetation_Cultivation area liable to flooding,Vegetation_Cultivation area with trees,Vegetation_Cultivation area without trees,Vegetation_Dense Forest,Vegetation_Galery Forest,Vegetation_Grassland,Vegetation_Grassland Savanna,Vegetation_Light Forest,Vegetation_Mangrove,Vegetation_Mine-Quarry,Vegetation_Plantation,Vegetation_Rice field,Vegetation_Rocky Terrain,Vegetation_Shrub Savanna,Vegetation_Swampy-Marshy-Wetland,Vegetation_Tree Savanna,Hydro_Lake Surface,Landuse_Activity area,Landuse_Cemetery,Landuse_Natural soil,Landuse_Sports field,Infra_Energy_Facility,Hydro_Basin surface,Hydro_Canal Surface,Hydro_Dam Polygon,Rail_station,Rail_bridge polygon,Road Amenities_Facilities,Road_bridge Polygon
    <EMPTY> -> AttributeCreator_6
    <MISSING> -> AttributeCreator_6
    <NULL> -> AttributeCreator_6
    <UNFILTERED> -> AttributeCreator_6
    AOI -> GeometryFilter_4
    Building_Urban_built_up_area -> GeometryFilter_4
    Hydro_Surface Permanent -> GeometryFilter_4
    Hydro_Surface Temporary -> GeometryFilter_4
    Vegetation_Bare Soil -> GeometryFilter_4
    Vegetation_Cultivation area liable to flooding -> GeometryFilter_4
    Vegetation_Cultivation area with trees -> GeometryFilter_4
    Vegetation_Cultivation area without trees -> GeometryFilter_4
    Vegetation_Dense Forest -> GeometryFilter_4
    Vegetation_Galery Forest -> GeometryFilter_4
    Vegetation_Grassland -> GeometryFilter_4
    Vegetation_Grassland Savanna -> GeometryFilter_4
    Vegetation_Light Forest -> GeometryFilter_4
    Vegetation_Mangrove -> GeometryFilter_4
    Vegetation_Mine-Quarry -> GeometryFilter_4
    Vegetation_Plantation -> GeometryFilter_4
    Vegetation_Rice field -> GeometryFilter_4
    Vegetation_Rocky Terrain -> GeometryFilter_4
    Vegetation_Shrub Savanna -> GeometryFilter_4
    Vegetation_Swampy-Marshy-Wetland -> GeometryFilter_4
    Vegetation_Tree Savanna -> GeometryFilter_4
    Hydro_Lake Surface -> GeometryFilter_4
    Building_Polygon -> GeometryFilter_4
    Landuse_Activity area -> GeometryFilter_4
    Landuse_Cemetery -> GeometryFilter_4
    Landuse_Natural soil -> GeometryFilter_4
    Landuse_Sports field -> GeometryFilter_4
    Infra_Energy_Facility -> GeometryFilter_4
    Hydro_Basin surface -> GeometryFilter_4
    Hydro_Canal Surface -> GeometryFilter_4
    Hydro_Dam Polygon -> GeometryFilter_4
    Rail_station -> GeometryFilter_4
    Rail_bridge polygon -> GeometryFilter_4
    Road Amenities_Facilities -> GeometryFilter_4
    Road_bridge Polygon -> GeometryFilter_4
AttributeCreator_6
    ATTR_TABLE = SET_TO igds_level_name = ERR_Wrong_Level_Name_@Value(igds_level_name)
    -> Level1 (writer DGNV8_2)
GeometryFilter_4
    BREAK_AGG = No
    GEOM_PORT_NAMES = Point Line Area
    POINT -> AttributeCreator_7
    LINE -> AttributeCreator_8
    AREA -> AreaOnAreaOverlayer_4 [AREA]
    <UNFILTERED> -> AttributeCreator_5
AttributeCreator_5
    ATTR_TABLE = SET_TO igds_level_name = ERR_Invalid_geometry_@Value(igds_level_name)
    -> Level1 (writer DGNV8_2)
AreaOnAreaOverlayer_4
    ACCUM_ATTRS_NAME = Use Attributes From One Feature
    CLEANING_TOLERANCE = 0.0001
    CONNECT_Z_MODE = First Wins
    DEAGGREGATE_INPUT = Yes
    LIST_ATTRS_TO_INCLUDE = igds_level_name
    LIST_NAME = _area
    OVC_ATTR = _overlaps
    AREA -> TestFilter
    REMNANTS -> AttributeCreator_4
    <REJECTED> -> AttributeCreator_4
TestFilter
    DEFAULT_VALUE = <UNFILTERED>
    TEST_LIST = "BOOL_OP,OR,COMPOSITE_TEST,""""""1"""""",TEST_CLAUSE,TEST @Value(_overlaps) = 1",GAP_Data,"BOOL_OP,OR,COMPOSITE_TEST,""""""1"""""",TEST_CLAUSE,TEST @Value(_overlaps) = 2",No Overlap,"BOOL_OP,OR,COMPOSITE_TEST,""""""1"""""",TEST_CLAUSE,TEST @Value(_overlaps) = 3",One_Layer-Overlap,"BOOL_OP,OR,COMPOSITE_TEST,""""""1"""""",TEST_CLAUSE,TEST @Value(_overlaps) = 4",Two_Layer-Overlap,"BOOL_OP,OR,COMPOSITE_TEST,""""""1"""""",TEST_CLAUSE,TEST @Value(_overlaps) = 5",Three_Layer-Overlap,"BOOL_OP,OR,COMPOSITE_TEST,""""""1"""""",TEST_CLAUSE,TEST @Value(_overlaps) = 6",Four_Layer-Overlap,"BOOL_OP,OR,COMPOSITE_TEST,""""""1"""""",TEST_CLAUSE,TEST @Value(_overlaps) = 7",Five_Layer-Overlap,"BOOL_OP,OR,COMPOSITE_TEST,""""""1"""""",TEST_CLAUSE,TEST @Value(_overlaps) = 8",Six_Layer-Overlap,"BOOL_OP,OR,COMPOSITE_TEST,""""""1"""""",TEST_CLAUSE,TEST @Value(_overlaps) = 9",Seven_Layer-Overlap,"BOOL_OP,OR,COMPOSITE_TEST,""""""1"""""",TEST_CLAUSE,TEST @Value(_overlaps) = 10",Eight_Layer-Overlap
    GAP_Data -> AttributeCreator
    No Overlap -> AttributeCreator_2
    One_Layer-Overlap -> Junction_2
    Two_Layer-Overlap -> Junction_2
    Three_Layer-Overlap -> Junction_2
    Four_Layer-Overlap -> Junction_2
    Five_Layer-Overlap -> Junction_2
    <UNFILTERED> -> Junction_2
    Six_Layer-Overlap -> Junction_2
    Seven_Layer-Overlap -> Junction_2
    Eight_Layer-Overlap -> Junction_2
AttributeCreator
    ATTR_TABLE = SET_TO igds_level_name = Err_Gap_@Value(igds_level_name)
    -> Level1 (writer DGNV8_2)
AttributeCreator_2
    ATTR_TABLE = SET_TO igds_level_name = NO_ERRS_@Value(igds_level_name)
Junction_2
    -> AttributeCreator_3
AttributeCreator_3
    ATTR_TABLE = SET_TO igds_level_name = ERR_Overlap_@Value(igds_level_name)
    -> Level1 (writer DGNV8_2)
AttributeCreator_4
    ATTR_TABLE = SET_TO igds_level_name = ERR_Others_@Value(igds_level_name)
    -> Level1 (writer DGNV8_2)
AttributeCreator_7
    ATTR_TABLE = SET_TO igds_level_name = ERR_Point_@Value(igds_level_name)
    -> Level1 (writer DGNV8_2)
AttributeCreator_8
    ATTR_TABLE = SET_TO igds_level_name = ERR_Line_@Value(igds_level_name)
    -> Level1 (writer DGNV8_2)
Level1 (writer DGNV8_2)
