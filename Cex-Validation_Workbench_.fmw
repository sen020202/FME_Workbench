FME workspace Cex-Validation_Workbench_.fmw

Parameters:
- SourceDataset_DGNV8 = $(FME_MF_DIR)Block_09.dgn   # Source Bentley MicroStation Design File(s)
- FEATURE_TYPES-SELECT_ALL_THE_LEVELS = Bench Big_Advertise_Signpost Border Bottom of slope Bridge Brushwood Building in ruins Canal circular manhole Concrete safety barrier Continuous line - solid line Default Discontinous line - broken line Double bench Electric Pole Fence Fire hydrant Flagstone-terrace Generic Signpost Give Way Signpost Grass Greenhouse Lamp post Landmark light Lane-Footpath Main Buildings Material_Direction_island Metal safety barrier Narrow-Ditch_Slope_top Other Buildings Paint marks on sports ground Paint_line_Ground-143 Paint_line_Ground-144 Paint_line_Ground-145 Paint_line_Ground-146 Paint_line_Ground-147 Palm tree Parking area Pedestrian bridge Pedestrian crossing Pedestrian Track Pedestrian traffic light planter-public spaces Pond Portal post line Power line Pylon row Railway line Train Reservoir-Silo Retaining wall base Retaining wall top roadside Roadside drain Rock area Roof ridge Round Signpost Sanitation grid Service cabinet Sidewalk small post Speed bump Sports ground square manhole Square Signpost Stairway Stream-riverside Swimming Pool Telecom single pole Top of slope Tree Triangular Signpost Vegetation alignment Wall Wall (axis) waste container Wood 2 402 AOI Big_Advertise_Board EDGEMATCH ERROR Growing area LIDAR MISSMATCH Major contours Ordinary contours Plate network not identified PointLevel Telecom_tower-Antenna Telecom-Tower
- DESTINATION_DGN-PATH = \\lgs-net.com\ablr\ablrdata\Exchange\Paso\fme\err\Cedex_Validation_FME-Errors_Block-4.dgn   # Destination Bentley MicroStation Design File

Readers:
- DGNV8_1: DGNV8 from $(SourceDataset_DGNV8)

Writers:
- DGNV8_2: DGNV8 to $(DESTINATION_DGN-PATH)

Note: INPUT Details
AttributeExposer
    ATTR_LIST = igds_level,igds_level_name,igds_cell_x_scale,igds_cell_y_scale,igds_cell_z_scale,igds_cell_element_level_name,igds_cell_element_level,igds_cell_name
    -> Counter
AttributeCreator_4
    ATTR_TABLE = SET_TO Error_Level = Err_Geometry_Type_Point
    -> Junction_5
Junction_13
    -> TestFilter_8-Single-PT
AttributeRounder_6
    PLACES = 4
    ROUND_TYPE = Nearest
    SRC_ATTRS = igds_cell_y_scale igds_cell_x_scale igds_cell_z_scale
    -> TestFilter_8
AttributeCreator_17
    ATTR_TABLE = SET_TO Error_Level = Err_Cell_Scale_Wrong
    -> Junction_9
AttributeCreator_16
    ATTR_TABLE = SET_TO Error_Level = Err_Cell_Rotation_Wrong
    -> Junction_9
AttributeCreator_15
    ATTR_TABLE:
      SET_TO Error_Level = Err_CellNAME or LevelNAME
      SET_TO Error_Text = Err_CellNAME or LevelNAME
      SET_TO idgs_text_string = @Value(Error_Text)
    -> Junction_9
Junction_9
    -> AttributeCreator_7
AttributeCreator_3
    ATTR_TABLE = SET_TO Error_Level = Err_Geometry_Type_Line
    -> Junction_5
AttributeCreator_2
    ATTR_TABLE = SET_TO Error_Level = Err_Level_Name
    -> Junction_5
AttributeCreator_5
    ATTR_TABLE = SET_TO Error_Level = Err_Geometry_Type_Shape
    -> Junction_5
Junction_8
    -> AttributeCreator_7
Note: Near 10CM vertex - in the objects
Junction_5
    -> AttributeCreator_7

Bookmark: Input_DESIGN file
small post (reader DGNV8_1)
    attributes: ufid_low integer, ufid_high integer, dgnfile integer
    -> AttributeExposer

Bookmark: Add Object ID for each element
Counter
    CNT_ATTR = OBJ_ID
    DOMAIN = counter
    SCOPE = Global
    START = 1
    -> GeometryValidator
    -> GeometryFilter
    -> TestFilter_18
    -> TestFilter_30

Bookmark: TEXT_MISMATCH_POLYGON
TestFilter_30
    DEFAULT_VALUE = Wrong_Text_Errors
    PASSED_TEST_GROUP_OUTPUT = FIRST
    TEST_LIST:
      "BOOL_OP,AND,COMPOSITE_TEST,""""""1 AND 2"""""",TEST_CLAUSE,TEST @Value(igds_level_name) = DAM
      TEST @Value(fme_text_string) = SLUICE",DAM,"BOOL_OP,AND,COMPOSITE_TEST,""""""1 AND 2"""""",TEST_CLAUSE,TEST @Value(igds_level_name) = Reservoir-Silo
      TEST @Value(fme_text_string) = SILO",SILO,"BOOL_OP,AND,COMPOSITE_TEST,""""""1 AND 2"""""",TEST_CLAUSE,TEST @Value(igds_level_name) = Telecom-Tower
      TEST @Value(fme_text_string) = ANTENNA",ANTENNA
    DAM -> PointOnAreaOverlayer [POINT]
    SILO -> PointOnAreaOverlayer [POINT]
    ANTENNA -> PointOnAreaOverlayer [POINT]
    Wrong_Text_Errors -> TestFilter_33
TestFilter_33
    DEFAULT_VALUE = Wrong_Text_Errors
    PASSED_TEST_GROUP_OUTPUT = FIRST
    TEST_LIST = "BOOL_OP,AND,COMPOSITE_TEST,""""""1"""""",TEST_CLAUSE,TEST @Value(igds_level_name) = DAM",DAM,"BOOL_OP,AND,COMPOSITE_TEST,""""""1"""""",TEST_CLAUSE,TEST @Value(igds_level_name) = Reservoir-Silo",SILO,"BOOL_OP,AND,COMPOSITE_TEST,""""""1"""""",TEST_CLAUSE,TEST @Value(igds_level_name) = Telecom-Tower",ANTENNA
    DAM -> PointOnAreaOverlayer [AREA]
    SILO -> PointOnAreaOverlayer [AREA]
    ANTENNA -> Bufferer_4
Bufferer_4
    ANGLE = 22.5
    CAP_STYLE = Arc
    CORNER_STYLE = Arc
    MODE = AREA
    OFFSET = 2
    OFFSET_UNITS = NONE
    PRECISION = APPROX
    BUFFERED -> PointOnAreaOverlayer [AREA]
PointOnAreaOverlayer
    ATTR_ACCUM_MODE = Prefic Incoming
    DEAGGREGATE_INPUT = Yes
    INCOMING_PREFIX = _POP_
    OV_ATTR = _overlaps
    POLYS_FIRST = NO
    POINT -> Tester_6
    AREA -> Tester_3
Tester_6
    BOOL_OP = OR
    TEST_CLAUSE = TEST @Value(_overlaps) = 1
    TEST_MODE = TEST
    FAILED -> AttributeCreator_32
AttributeCreator_32
    ATTR_TABLE = SET_TO Error_Level = POLYGON_NOT_INSIDE_TEXT
    -> Junction_15
Tester_3
    BOOL_OP = OR
    TEST_CLAUSE = TEST @Value(_overlaps) = 1
    TEST_MODE = TEST
    FAILED -> AttributeCreator_33
AttributeCreator_33
    ATTR_TABLE = SET_TO Error_Level = TEXT_NOT_INSIDE_FEATURE
    -> Junction_15
Junction_15
    -> AttributeCreator_7

Bookmark: ALtimetric-points distribution missing-not all as errors
Note: Altimetric point missing errors-May have some false positive
TestFilter_18
    DEFAULT_VALUE = <UNFILTERED>
    PASSED_TEST_GROUP_OUTPUT = FIRST
    TEST_LIST:
      "BOOL_OP,OR,COMPOSITE_TEST,""""""1 OR 2"""""",TEST_CLAUSE,TEST @Value(igds_level_name) = Altimetric point
      TEST @Value(igds_level_name) = Altimetric point crossroads axis",for alti-point check,"BOOL_OP,OR,COMPOSITE_TEST,""""""1"""""",TEST_CLAUSE,TEST @Value(igds_level_name) = Flagstone-terrace",Flagstone-terrace,"BOOL_OP,OR,COMPOSITE_TEST,""""""1"""""",TEST_CLAUSE,TEST @Value(igds_level_name) = Pond",Pond,"BOOL_OP,OR,COMPOSITE_TEST,""""""1"""""",TEST_CLAUSE,TEST @Value(igds_level_name) = Swimming Pool",Swimming Pool,"BOOL_OP,OR,COMPOSITE_TEST,""""""1"""""",TEST_CLAUSE,TEST @Value(igds_level_name) = Parking area",Parking area,"BOOL_OP,OR,COMPOSITE_TEST,""""""1"""""",TEST_CLAUSE,TEST @Value(igds_level_name) = Greenhouse",Greenhouse,"BOOL_OP,OR,COMPOSITE_TEST,""""""1"""""",TEST_CLAUSE,TEST @Value(igds_level_name) = Building in ruins",Building in ruins,"BOOL_OP,OR,COMPOSITE_TEST,""""""1"""""",TEST_CLAUSE,TEST @Value(igds_level_name) = Other Buildings",Other Buildings,"BOOL_OP,OR,COMPOSITE_TEST,""""""1"""""",TEST_CLAUSE,TEST @Value(igds_level_name) = Main Buildings",Main Buildings,"BOOL_OP,OR,COMPOSITE_TEST,""""""1"""""",TEST_CLAUSE,TEST @Value(igds_level_name) = roadside",roadside,"BOOL_OP,OR,COMPOSITE_TEST,""""""1"""""",TEST_CLAUSE,TEST @Value(igds_level_name) = Boundary",Boundary
    for alti-point check -> Bufferer
    Flagstone-terrace -> Junction_3
    Pond -> Junction_3
    Swimming Pool -> Junction_3
    Parking area -> Junction_3
    Greenhouse -> Junction_3
    Building in ruins -> Junction_3
    Other Buildings -> Junction_3
    Main Buildings -> Junction_3
    Boundary -> Clipper_2 [CLIPPER]
Junction_3
    -> Clipper_2 [CLIPPEE]
CenterPointExtractor
    CENTX = _inside_x
    CENTY = _inside_y
    CENTZ = _inside_z
    EXTRACTIONMODE = CENTER
    -> VertexCreator
VertexCreator
    MEASURE_TYPE = Continuous
    MODE_NAME = Replace with Point
    XVAL = @Value(_inside_x)
    YVAL = @Value(_inside_y)
    ZVAL = @Value(_inside_z)
    -> Bufferer
Bufferer
    ANGLE = 22.5
    CAP_STYLE = Round
    CORNER_STYLE = Round
    MODE = AREA
    OFFSET = 15
    OFFSET_UNITS = NONE
    BUFFERED -> Clipper_2 [CLIPPEE]
Clipper_2
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Dissolver_2
Dissolver_2
    ACCUM_INPUT_ATTRS = Use Attributes From One Feature
    CLEANING_TOLERANCE = Automatic
    CONNECT_Z_MODE = First Wins
    DEAGGREGATE_INPUT = Yes
    AREA -> DonutHoleExtractor
DonutHoleExtractor
    DEAGGREGATE_INPUT = Yes
    HOLE -> AreaCalculator_2
AreaCalculator_2
    AREA_ATTR = Void_Area
    AREA_TYPE = Plane Area
    MULT = 1
    -> TestFilter_19
TestFilter_19
    DEFAULT_VALUE = <UNFILTERED>
    PASSED_TEST_GROUP_OUTPUT = FIRST
    TEST_LIST = "BOOL_OP,OR,COMPOSITE_TEST,""""""1"""""",TEST_CLAUSE,TEST @Value(Void_Area) >= 50",50
    50 -> CenterPointExtractor_2
CenterPointExtractor_2
    CENTX = _inside_x
    CENTY = _inside_y
    CENTZ = _inside_z
    EXTRACTIONMODE = CENTER
    -> AttributeCreator_20
AttributeCreator_20
    ATTR_TABLE = SET_TO Error_Level = CHECK_Missing_Alti_Points
    -> AttributeCreator_7

Bookmark: Geometry_VALIDATOR_CHECK
GeometryValidator
    ISSUE_ATTR_NAME = Validation_Issues
    PRESETS = Custom
    REPAIR = No
    RULES = AREA_ORIENTATION AREA_ORIENTATION]LEFT]FME_CONTROLLER_QUERY_FILE]transformers/dependencies/geometryvalidator/AREA_ORIENTATION.fme NAN_REMOVAL PROCESS_MEASURE]NO]FME_CONTROLLER_QUERY_FILE]transformers/dependencies/geometryvalidator/NAN_REMOVAL.fme SELF_INTERSECTING CHECK_HOLE_TOUCHING_POLYGON]Yes]CONNECT_Z_MODE_SI]IGNORE_Z]SELF_INTERSECTION_TOLERANCE]Automatic]FME_CONTROLLER_QUERY_FILE]transformers/dependencies/geometryvalidator/SELF_INTERSECTING.fme CONSECUTIVE_IDENTICAL_VERTICES_2D CHECK_Z]NO]TOLERANCE]0.001]FME_CONTROLLER_QUERY_FILE]transformers/dependencies/geometryvalidator/CONSECUTIVE_IDENTICAL_VERTICES_2D.fme MISSING_VERTEX_NORMALS  OGC_SIMPLE_CHECK  OGC_VALID_CHECK OGC_VERSION]V1.2.0]FME_CONTROLLER_QUERY_FILE]transformers/dependencies/geometryvalidator/OGC_VALID_CHECK.fme
    SUMMARY = Detailed
    ISSUE_LOCATIONS -> Tester
Tester
    BOOL_OP = OR
    TEST_CLAUSE = TEST @Value(issue_found) = Self-Intersections in 2D
    TEST_MODE = TEST
    PASSED -> AttributeCreator_19
Note: Geometry_VALIDATOR_CHECK
AttributeCreator_19
    ATTR_TABLE = SET_TO Error_Level = Err_Validation
    -> AttributeCreator_7

Bookmark: Geometry type check
GeometryFilter
    BREAK_AGG = No
    GEOM_PORT_NAMES = Point Line Area Text
    POINT -> TestFilter
    LINE -> TestFilter_4
    LINE -> TestFilter_14
    AREA -> TestFilter_3
    TEXT -> TestFilter_2
    <UNFILTERED> -> AttributeCreator_2
TestFilter
    DEFAULT_VALUE = Not_allowed_points
    PASSED_TEST_GROUP_OUTPUT = FIRST
    TEST_LIST:
      "BOOL_OP,OR,COMPOSITE_TEST,""""""1 OR 2"""""",TEST_CLAUSE,TEST @Value(igds_level_name) = Altimetric point crossroads axis
      TEST @Value(igds_level_name) = Altimetric point",@Value(igds_level) = Altimetric point & crossroads points,"BOOL_OP,OR,COMPOSITE_TEST,""""""1 OR 2 OR 3 OR 4 OR 5 OR 6 OR 7 OR 8 OR 9 OR 10 OR 11 OR 12 OR 13 OR 14 OR 15 OR 16 OR 17 OR 18 OR 19 OR 20 OR 21 OR 22 OR 23 OR 24 OR 25 OR 26 OR 27 OR 28 OR 29 OR 30 OR 31 OR 32 OR 33 OR 34 OR 35 OR 36 OR 37"""""",TEST_CLAUSE,TEST @Value(igds_level_name) = Electric Pole
      TEST @Value(igds_level_name) = circular manhole
      TEST @Value(igds_level_name) = small post
      TEST @Value(igds_level_name) = Bus shelters
      TEST @Value(igds_level_name) = Bench
      TEST @Value(igds_level_name) = Double bench
      TEST @Value(igds_level_name) = Gantry 1 support
      TEST @Value(igds_level_name) = Gantry_with2_Support
      TEST @Value(igds_level_name) = waste container
      TEST @Value(igds_level_name) = Landmark light
      TEST @Value(igds_level_name) = Pylon row
      TEST @Value(igds_level_name) = Roadside drain
      TEST @Value(igds_level_name) = Sanitation grid
      TEST @Value(igds_level_name) = Plate_network_not_identified
      TEST @Value(igds_level_name) = Lamp post
      TEST @Value(igds_level_name) = Telecom-Tower
      TEST @Value(igds_level_name) = Service cabinet
      TEST @Value(igds_level_name) = Paint_line_Ground-144
      TEST @Value(igds_level_name) = Paint_line_Ground-145
      TEST @Value(igds_level_name) = square manhole
      TEST @Value(igds_level_name) = Telecom single pole
      TEST @Value(igds_level_name) = Paint_line_Ground-147
      TEST @Value(igds_level_name) = Paint_line_Ground-148
      TEST @Value(igds_level_name) = Paint_line_Ground-143
      TEST @Value(igds_level_name) = Paint_line_Ground-149
      TEST @Value(igds_level_name) = Pedestrian traffic light
      TEST @Value(igds_level_name) = Stop Signpost
      TEST @Value(igds_level_name) = Traffic light
      TEST @Value(igds_level_name) = Paint_line_Ground-146
      TEST @Value(igds_level_name) = Round Signpost
      TEST @Value(igds_level_name) = Square Signpost
      TEST @Value(igds_level_name) = Triangular Signpost
      TEST @Value(igds_level_name) = Give Way Signpost
      TEST @Value(igds_level_name) = Generic Signpost
      TEST @Value(igds_level_name) = Tree
      TEST @Value(igds_level_name) = Palm tree
      TEST @Value(igds_level_name) = Fire hydrant",For_Cell_Features
    @Value(igds_level) = Altimetric point & crossroads points -> TestFilter_10
    For_Cell_Features -> Junction_13
    Not_allowed_points -> AttributeCreator_4
TestFilter_4
    DEFAULT_VALUE = Non-Line_Layers
    PASSED_TEST_GROUP_OUTPUT = FIRST
    TEST_LIST:
      "BOOL_OP,OR,COMPOSITE_TEST,""""""1 OR 2 OR 3 OR 4 OR 5 OR 6 OR 7 OR 8 OR 9 OR 10 OR 11 OR 12 OR 13 OR 14 OR 15 OR 16 OR 17 OR 18 OR 19 OR 20 OR 21 OR 22 OR 23 OR 24 OR 25 OR 26 OR 27 OR 28 OR 29 OR 30 OR 31 OR 32 OR 33 OR 34 OR 35 OR 36 OR 37 OR 38 OR 39 OR 40"""""",TEST_CLAUSE,TEST @Value(igds_level_name) = Paint marks on sports ground
      TEST @Value(igds_level_name) = Airport runway
      TEST @Value(igds_level_name) = Roof ridge
      TEST @Value(igds_level_name) = Stairway
      TEST @Value(igds_level_name) = Fence
      TEST @Value(igds_level_name) = Wall (axis)
      TEST @Value(igds_level_name) = Portal
      TEST @Value(igds_level_name) = Retaining wall top
      TEST @Value(igds_level_name) = Retaining wall base
      TEST @Value(igds_level_name) = Coast line
      TEST @Value(igds_level_name) = Canal
      TEST @Value(igds_level_name) = Dock or river dock
      TEST @Value(igds_level_name) = Stream-riverside
      TEST @Value(igds_level_name) = Rock dyke
      TEST @Value(igds_level_name) = post line
      TEST @Value(igds_level_name) = Concrete dyke
      TEST @Value(igds_level_name) = Narrow-Ditch_Slope_top
      TEST @Value(igds_level_name) = Ordinary contours
      TEST @Value(igds_level_name) = Top of slope
      TEST @Value(igds_level_name) = Bottom of slope
      TEST @Value(igds_level_name) = Major contours
      TEST @Value(igds_level_name) = Rock area
      TEST @Value(igds_level_name) = Continuous line - solid line
      TEST @Value(igds_level_name) = Discontinous line - broken line
      TEST @Value(igds_level_name) = Railway line Train
      TEST @Value(igds_level_name) = Railway dock
      TEST @Value(igds_level_name) = Tram line
      TEST @Value(igds_level_name) = Vegetation alignment
      TEST @Value(igds_level_name) = Metal safety barrier
      TEST @Value(igds_level_name) = Concrete safety barrier
      TEST @Value(igds_level_name) = roadside
      TEST @Value(igds_level_name) = Pedestrian bridge
      TEST @Value(igds_level_name) = Lane-Footpath
      TEST @Value(igds_level_name) = Bridge
      TEST @Value(igds_level_name) = Sidewalk
      TEST @Value(igds_level_name) = overpass
      TEST @Value(igds_level_name) = Cycling Path
      TEST @Value(igds_level_name) = Pedestrian Track
      TEST @Value(igds_level_name) = Big_Advertise_Signpost
      TEST @Value(igds_level_name) = Power line",Line_features
    Line_features -> TestFilter_5_-VERTEX_COUNT_CHECK
    Line_features -> TestFilter_10
    Line_features -> TestFilter_16
    Line_features -> TestFilter_6
    Line_features -> TestFilter_23
    Line_features -> Junction_11
    Non-Line_Layers -> AttributeCreator_3
    Non-Line_Layers -> TestFilter_29
TestFilter_3
    DEFAULT_VALUE = NON_POLYGON_Layers
    PASSED_TEST_GROUP_OUTPUT = FIRST
    TEST_LIST:
      "BOOL_OP,OR,COMPOSITE_TEST,""""""1 OR 2 OR 3 OR 4 OR 5 OR 6 OR 7 OR 8 OR 9 OR 10 OR 11 OR 12 OR 13 OR 14 OR 15 OR 16 OR 17 OR 18 OR 19 OR 20 OR 21 OR 22 OR 23 OR 24 OR 25 OR 26 OR 27 OR 28 OR 29"""""",TEST_CLAUSE,TEST @Value(igds_level_name) = Sports ground
      TEST @Value(igds_level_name) = Other Buildings
      TEST @Value(igds_level_name) = Graveyard perimiter
      TEST @Value(igds_level_name) = Main Buildings
      TEST @Value(igds_level_name) = Flagstone-terrace
      TEST @Value(igds_level_name) = Greenhouse
      TEST @Value(igds_level_name) = Wall
      TEST @Value(igds_level_name) = Building in ruins
      TEST @Value(igds_level_name) = Pond
      TEST @Value(igds_level_name) = Beach
      TEST @Value(igds_level_name) = Swimming Pool
      TEST @Value(igds_level_name) = Swamp
      TEST @Value(igds_level_name) = Pontoon
      TEST @Value(igds_level_name) = Telecom-Tower
      TEST @Value(igds_level_name) = DAM
      TEST @Value(igds_level_name) = planter-public spaces
      TEST @Value(igds_level_name) = Reservoir-Silo
      TEST @Value(igds_level_name) = Parking area
      TEST @Value(igds_level_name) = Speed bump
      TEST @Value(igds_level_name) = Pedestrian crossing
      TEST @Value(igds_level_name) = Material_Direction_island
      TEST @Value(igds_level_name) = Wood
      TEST @Value(igds_level_name) = Grass
      TEST @Value(igds_level_name) = Cultivation_area
      TEST @Value(igds_level_name) = Brushwood
      TEST @Value(igds_level_name) = Border
      TEST @Value(igds_level_name) = automatic public toilet
      TEST @Value(igds_level_name) = Taxi area
      TEST @Value(igds_level_name) = Stairway",Polygon_features
    Polygon_features -> TestFilter_5_-VERTEX_COUNT_CHECK
    Polygon_features -> TestFilter_7
    Polygon_features -> TestFilter_10
    Polygon_features -> OrientationExtractor
    Polygon_features -> TestFilter_15
    Polygon_features -> TestFilter_16
    Polygon_features -> TestFilter_6
    Polygon_features -> TestFilter_22
    Polygon_features -> TestFilter_32
    NON_POLYGON_Layers -> AttributeCreator_5
TestFilter_2
    DEFAULT_VALUE = Wrong_Text_Errors
    PASSED_TEST_GROUP_OUTPUT = FIRST
    TEST_LIST:
      "BOOL_OP,AND,COMPOSITE_TEST,""""""1 AND 2"""""",TEST_CLAUSE,TEST @Value(igds_level_name) = DAM
      TEST @Value(fme_text_string) = SLUICE",DAM,"BOOL_OP,AND,COMPOSITE_TEST,""""""1 AND 2"""""",TEST_CLAUSE,TEST @Value(igds_level_name) = Reservoir-Silo
      TEST @Value(fme_text_string) = SILO",SILO,"BOOL_OP,AND,COMPOSITE_TEST,""""""1 AND 2"""""",TEST_CLAUSE,TEST @Value(igds_level_name) = Telecom-Tower
      TEST @Value(fme_text_string) = ANTENNA",ANTENNA
    Wrong_Text_Errors -> AttributeCreator_6
AttributeCreator_6
    ATTR_TABLE = SET_TO Error_Level = Err_TEXT_Wrong
    -> Junction_5

Bookmark: New Bookmark
TestFilter_14
    DEFAULT_VALUE = <UNFILTERED>
    PASSED_TEST_GROUP_OUTPUT = FIRST
    TEST_LIST = "BOOL_OP,AND,COMPOSITE_TEST,""""""1"""""",TEST_CLAUSE,TEST @Value(igds_level_name) = Retaining wall top",Retaining wall top,"BOOL_OP,OR,COMPOSITE_TEST,""""""1"""""",TEST_CLAUSE,TEST @Value(igds_level_name) = Narrow-Ditch_Slope_top",Narrow-Ditch_Slope_top,"BOOL_OP,OR,COMPOSITE_TEST,""""""1"""""",TEST_CLAUSE,TEST @Value(igds_level_name) = Top of slope",Top of slope,"BOOL_OP,OR,COMPOSITE_TEST,""""""1"""""",TEST_CLAUSE,TEST @Value(igds_level_name) = Bottom of slope",Bottom of slope,"BOOL_OP,OR,COMPOSITE_TEST,""""""1"""""",TEST_CLAUSE,TEST @Value(igds_level_name) = Retaining wall base",Retaining wall base
    Narrow-Ditch_Slope_top -> LineCombiner
    Top of slope -> LineCombiner_3
    Bottom of slope -> LineCombiner_2
LineCombiner
    ACCUM_ATTRS_NAME = Use Attributes From One Feature
    BREAK = no
    BREAK_CONNECTION_ATTRIBUTES = igds_level_name
    CONSIDER_NODE_ELEVATION = yes
    DEAGGREGATE_GEOMETRY = Deaggregate
    JUNCTIONS_IGNORE_ATTRIBUTES = No
    LINES_AS_SEGMENTS = No
    PRESERVE = no
    TOPOLOGY = Vertex noded
    LINE -> LineOnLineOverlayer_2 [LINE]
LineCombiner_3
    ACCUM_ATTRS_NAME = Use Attributes From One Feature
    BREAK = no
    BREAK_CONNECTION_ATTRIBUTES = igds_level_name
    CONSIDER_NODE_ELEVATION = yes
    DEAGGREGATE_GEOMETRY = Deaggregate
    JUNCTIONS_IGNORE_ATTRIBUTES = No
    LINES_AS_SEGMENTS = No
    PRESERVE = no
    TOPOLOGY = Vertex noded
    LINE -> LineOnLineOverlayer_2 [LINE]
LineCombiner_2
    ACCUM_ATTRS_NAME = Use Attributes From One Feature
    BREAK = no
    BREAK_CONNECTION_ATTRIBUTES = igds_level_name
    CONSIDER_NODE_ELEVATION = yes
    DEAGGREGATE_GEOMETRY = Deaggregate
    JUNCTIONS_IGNORE_ATTRIBUTES = No
    LINES_AS_SEGMENTS = No
    PRESERVE = no
    TOPOLOGY = Vertex noded
    LINE -> LineOnLineOverlayer_2 [LINE]
LineOnLineOverlayer_2
    ATTRS_ACCUM_MODE = Merge Attributes
    CLEANING_TOLERANCE = Automatic
    DEAGGREGATE_INPUT = Yes
    GENERATE_LIST_DROP = YES
    INCOMING_PREFIX = "_new "
    LIST_ATTRS_TO_INCLUDE = igds_level_name
    LIST_NAME = New
    OV_ATTR = _overlaps
    SEPARATE_COLLINEAR_SEGMENTS = No
    POINT -> TestFilter_25
Note: Slope wrong snapping issues
TestFilter_25
    DEFAULT_VALUE = <UNFILTERED>
    PASSED_TEST_GROUP_OUTPUT = FIRST
    TEST_LIST:
      "BOOL_OP,AND,COMPOSITE_TEST,""""""1 AND 2"""""",TEST_CLAUSE,TEST @Value(New{0}.igds_level_name) = Bottom of slope
      TEST @Value(New{1}.igds_level_name) = Top of slope",OK,"BOOL_OP,AND,COMPOSITE_TEST,""""""1 AND 2"""""",TEST_CLAUSE,TEST @Value(New{1}.igds_level_name) = Bottom of slope
      TEST @Value(New{0}.igds_level_name) = Top of slope",OK,"BOOL_OP,AND,COMPOSITE_TEST,""""""1 AND 2"""""",TEST_CLAUSE,TEST @Value(New{1}.igds_level_name) = Top of slope
      TEST @Value(New{0}.igds_level_name) = Bottom of slope",OK,"BOOL_OP,AND,COMPOSITE_TEST,""""""1 AND 2"""""",TEST_CLAUSE,TEST @Value(New{1}.igds_level_name) = Top of slope
      TEST @Value(New{0}.igds_level_name) = Bottom of slope",OK
    <UNFILTERED> -> AttributeCreator_21
AttributeCreator_21
    ATTR_TABLE = SET_TO Error_Level = CHECK_Slope_Snapping_Issues
    -> AttributeCreator_7

Bookmark: -SINGLE_POINT CELL-LEVEL_NAME_VALIDATION
TestFilter_8-Single-PT
    DEFAULT_VALUE = <UNFILTERED>
    PASSED_TEST_GROUP_OUTPUT = FIRST
    TEST_LIST:
      "BOOL_OP,AND,COMPOSITE_TEST,""""""1 AND 2"""""",TEST_CLAUSE,TEST @Value(igds_cell_element_level_name) = small post
      TEST @Value(igds_cell_name) = PLOT",small post,"BOOL_OP,AND,COMPOSITE_TEST,""""""1 AND 2"""""",TEST_CLAUSE,TEST @Value(igds_cell_element_level_name) = Gantry 1 support
      TEST @Value(igds_cell_name) = CAT",Gantry 1 support,"BOOL_OP,AND,COMPOSITE_TEST,""""""1 AND 2"""""",TEST_CLAUSE,TEST @Value(igds_cell_element_level_name) = Landmark light
      TEST @Value(igds_cell_name) = LAMPSO",Landmark light,"BOOL_OP,AND,COMPOSITE_TEST,""""""1 AND 2"""""",TEST_CLAUSE,TEST @Value(igds_cell_element_level_name) = Lamp post
      TEST @Value(igds_cell_name) = LS",Lamp post,"BOOL_OP,AND,COMPOSITE_TEST,""""""1 AND 2"""""",TEST_CLAUSE,TEST @Value(igds_cell_element_level_name) = Electric Pole
      TEST @Value(igds_cell_name) = BT",Electric Pole,"BOOL_OP,AND,COMPOSITE_TEST,""""""1 AND 2"""""",TEST_CLAUSE,TEST @Value(igds_cell_element_level_name) = Fire hydrant
      TEST @Value(igds_cell_name) = BI",Fire hydrant,"BOOL_OP,AND,COMPOSITE_TEST,""""""1 AND 2"""""",TEST_CLAUSE,TEST @Value(igds_cell_element_level_name) = circular manhole
      TEST @Value(igds_cell_name) = C70",circular manhole,"BOOL_OP,AND,COMPOSITE_TEST,""""""1 AND 2"""""",TEST_CLAUSE,TEST @Value(igds_cell_element_level_name) = Telecom single pole
      TEST @Value(igds_cell_name) = FT",Telecom single pole,"BOOL_OP,AND,COMPOSITE_TEST,""""""1 AND 2"""""",TEST_CLAUSE,TEST @Value(igds_cell_element_level_name) = Telecom-Tower
      TEST @Value(igds_cell_name) = FT",Telecom-Tower,"BOOL_OP,AND,COMPOSITE_TEST,""""""1 AND 2"""""",TEST_CLAUSE,TEST @Value(igds_cell_element_level_name) = Pedestrian traffic light
      TEST @Value(igds_cell_name) = FP",Pedestrian traffic light,"BOOL_OP,AND,COMPOSITE_TEST,""""""1 AND 2"""""",TEST_CLAUSE,TEST @Value(igds_cell_element_level_name) = Traffic light
      TEST @Value(igds_cell_name) = FTRI",Traffic light,"BOOL_OP,AND,COMPOSITE_TEST,""""""1 AND 2"""""",TEST_CLAUSE,TEST @Value(igds_cell_element_level_name) = Stop Signpost
      TEST @Value(igds_cell_name) = PAN47",Stop Signpost,"BOOL_OP,AND,COMPOSITE_TEST,""""""1 AND 2"""""",TEST_CLAUSE,TEST @Value(igds_cell_element_level_name) = Round Signpost
      TEST @Value(igds_cell_name) = PAN41",Round Signpost,"BOOL_OP,AND,COMPOSITE_TEST,""""""1 AND 2"""""",TEST_CLAUSE,TEST @Value(igds_cell_element_level_name) = Square Signpost
      TEST @Value(igds_cell_name) = PAN45",Square Signpost,"BOOL_OP,AND,COMPOSITE_TEST,""""""1 AND 2"""""",TEST_CLAUSE,TEST @Value(igds_cell_element_level_name) = Triangular Signpost
      TEST @Value(igds_cell_name) = PAN43",Triangular Signpost,"BOOL_OP,AND,COMPOSITE_TEST,""""""1 AND 2"""""",TEST_CLAUSE,TEST @Value(igds_cell_element_level_name) = Give Way Signpost
      TEST @Value(igds_cell_name) = PAN42",Give Way Signpost,"BOOL_OP,AND,COMPOSITE_TEST,""""""1 AND 2"""""",TEST_CLAUSE,TEST @Value(igds_cell_element_level_name) = Generic Signpost
      TEST @Value(igds_cell_name) = PAN40",Generic Signpost,"BOOL_OP,AND,COMPOSITE_TEST,""""""1 AND 2"""""",TEST_CLAUSE,TEST @Value(igds_cell_element_level_name) = Tree
      TEST @Value(igds_cell_name) = ARB",Tree,"BOOL_OP,AND,COMPOSITE_TEST,""""""1 AND 2"""""",TEST_CLAUSE,TEST @Value(igds_cell_element_level_name) = Palm tree
      TEST @Value(igds_cell_name) = PALM",Palm tree
    small post -> Junction
    Gantry 1 support -> Junction
    Landmark light -> Junction
    Lamp post -> Junction
    Electric Pole -> Junction
    Fire hydrant -> Junction
    circular manhole -> Junction
    Telecom single pole -> Junction
    Telecom-Tower -> Junction
    Pedestrian traffic light -> Junction
    Traffic light -> Junction
    Stop Signpost -> Junction
    Round Signpost -> Junction
    Square Signpost -> Junction
    Triangular Signpost -> Junction
    Give Way Signpost -> Junction
    Generic Signpost -> Junction
    Tree -> Junction
    Palm tree -> Junction
    <UNFILTERED> -> TestFilter_9-Other-Single-PT
Junction
    -> AttributeRounder_6
Note: For MULTI-POINT CELL LEVELS VALIDATION
TestFilter_9-Other-Single-PT
    DEFAULT_VALUE = <UNFILTERED>
    PASSED_TEST_GROUP_OUTPUT = FIRST
    TEST_LIST:
      "BOOL_OP,AND,COMPOSITE_TEST,""""""1 AND 2"""""",TEST_CLAUSE,TEST @Value(igds_cell_element_level_name) = Bus shelters
      TEST @Value(igds_cell_name) = PIL1",Bus shelters,"BOOL_OP,AND,COMPOSITE_TEST,""""""1 AND 2"""""",TEST_CLAUSE,TEST @Value(igds_cell_element_level_name) = Bench
      TEST @Value(igds_cell_name) = BANC",Bench,"BOOL_OP,AND,COMPOSITE_TEST,""""""1 AND 2"""""",TEST_CLAUSE,TEST @Value(igds_cell_element_level_name) = Double bench
      TEST @Value(igds_cell_name) = TRANSF",Double bench,"BOOL_OP,AND,COMPOSITE_TEST,""""""1 AND 2"""""",TEST_CLAUSE,TEST @Value(igds_cell_element_level_name) = Gantry_with2_Support
      TEST @Value(igds_cell_name) = CAT1",Gantry_with2_Support,"BOOL_OP,AND,COMPOSITE_TEST,""""""1 AND 2"""""",TEST_CLAUSE,TEST @Value(igds_cell_element_level_name) = waste container
      TEST @Value(igds_cell_name) = PIL1",waste container,"BOOL_OP,AND,COMPOSITE_TEST,""""""1 AND 2"""""",TEST_CLAUSE,TEST @Value(igds_cell_element_level_name) = Pylon row
      TEST @Value(igds_cell_name) = PIL1",Pylon row,"BOOL_OP,AND,COMPOSITE_TEST,""""""1 AND 2"""""",TEST_CLAUSE,TEST @Value(igds_cell_element_level_name) = Roadside drain
      TEST @Value(igds_cell_name) = AVAL",Roadside drain,"BOOL_OP,AND,COMPOSITE_TEST,""""""1 AND 2"""""",TEST_CLAUSE,TEST @Value(igds_cell_element_level_name) = Sanitation grid
      TEST @Value(igds_cell_name) = GRAS",Sanitation grid,"BOOL_OP,AND,COMPOSITE_TEST,""""""1 AND 2"""""",TEST_CLAUSE,TEST @Value(igds_cell_element_level_name) = Plate_network_not_identified
      TEST @Value(igds_cell_name) = PL",Plate_network_not_identified,"BOOL_OP,AND,COMPOSITE_TEST,""""""1 AND 2"""""",TEST_CLAUSE,TEST @Value(igds_cell_element_level_name) = Service cabinet
      TEST @Value(igds_cell_name) = TRANSF",Service cabinet,"BOOL_OP,AND,COMPOSITE_TEST,""""""1 AND 2"""""",TEST_CLAUSE,TEST @Value(igds_cell_element_level_name) = Paint_line_Ground-144
      TEST @Value(igds_cell_name) = FRABD",Paint_line_Ground-144,"BOOL_OP,AND,COMPOSITE_TEST,""""""1 AND 2"""""",TEST_CLAUSE,TEST @Value(igds_cell_element_level_name) = Paint_line_Ground-145
      TEST @Value(igds_cell_name) = FRABG",Paint_line_Ground-145,"BOOL_OP,AND,COMPOSITE_TEST,""""""1 AND 2"""""",TEST_CLAUSE,TEST @Value(igds_cell_element_level_name) = square manhole
      TEST @Value(igds_cell_name) = PL1",square manhole,"BOOL_OP,AND,COMPOSITE_TEST,""""""1 AND 2"""""",TEST_CLAUSE,TEST @Value(igds_cell_element_level_name) = Paint_line_Ground-147
      TEST @Value(igds_cell_name) = FBIG",Paint_line_Ground-147,"BOOL_OP,AND,COMPOSITE_TEST,""""""1 AND 2"""""",TEST_CLAUSE,TEST @Value(igds_cell_element_level_name) = Paint_line_Ground-148
      TEST @Value(igds_cell_name) = FDD",Paint_line_Ground-148,"BOOL_OP,AND,COMPOSITE_TEST,""""""1 AND 2"""""",TEST_CLAUSE,TEST @Value(igds_cell_element_level_name) = Paint_line_Ground-143
      TEST @Value(igds_cell_name) = FDIR",Paint_line_Ground-143,"BOOL_OP,AND,COMPOSITE_TEST,""""""1 AND 2"""""",TEST_CLAUSE,TEST @Value(igds_cell_element_level_name) = Paint_line_Ground-149
      TEST @Value(igds_cell_name) = FDG",Paint_line_Ground-149,"BOOL_OP,AND,COMPOSITE_TEST,""""""1 AND 2"""""",TEST_CLAUSE,TEST @Value(igds_cell_element_level_name) = Paint_line_Ground-146
      TEST @Value(igds_cell_name) = FBID",Paint_line_Ground-146
    Bus shelters -> Junction_2
    Bench -> Junction_2
    Double bench -> Junction_2
    Gantry_with2_Support -> Junction_2
    waste container -> Junction_2
    Pylon row -> Junction_2
    Roadside drain -> Junction_2
    Sanitation grid -> Junction_2
    Plate_network_not_identified -> Junction_2
    Service cabinet -> Junction_2
    Paint_line_Ground-144 -> Junction_2
    Paint_line_Ground-145 -> Junction_2
    square manhole -> Junction_2
    Paint_line_Ground-147 -> Junction_2
    Paint_line_Ground-148 -> Junction_2
    Paint_line_Ground-143 -> Junction_2
    Paint_line_Ground-149 -> Junction_2
    Paint_line_Ground-146 -> Junction_2
    <UNFILTERED> -> AttributeCreator_15
Junction_2
    -> TestFilter_9

Bookmark: For_SINGLE_CELL_SCALE_Validation
TestFilter_8
    DEFAULT_VALUE = CELL_Scale_Wrong-ONE_POINT
    PASSED_TEST_GROUP_OUTPUT = FIRST
    TEST_LIST:
      "BOOL_OP,AND,COMPOSITE_TEST,""""""1 AND 2 AND 3"""""",TEST_CLAUSE,TEST @Value(igds_cell_x_scale) = 0.5
      TEST @Value(igds_cell_y_scale) = 0.5
      TEST @Value(igds_cell_z_scale) = 0.5",CELL_Correct_Scale-ONE_POINT
    CELL_Scale_Wrong-ONE_POINT -> AttributeCreator_17
Note: For_Multi-CELL_ANGLE_Validation
TestFilter_9
    DEFAULT_VALUE = CELL SALE Correct
    PASSED_TEST_GROUP_OUTPUT = FIRST
    TEST_LIST = "BOOL_OP,OR,COMPOSITE_TEST,""""""1"""""",TEST_CLAUSE,TEST @Value(igds_rotation) = 0",ROTATION-0_Error
    ROTATION-0_Error -> AttributeCreator_16

Bookmark: New Bookmark
TestFilter_29
    DEFAULT_VALUE = not required-lines
    PASSED_TEST_GROUP_OUTPUT = FIRST
    TEST_LIST:
      "BOOL_OP,OR,COMPOSITE_TEST,""""""1 OR 2 OR 3 OR 4 OR 5 OR 6 OR 7 OR 8 OR 9 OR 10 OR 11 OR 12 OR 13"""""",TEST_CLAUSE,TEST @Value(igds_level_name) = Coast line
      TEST @Value(igds_level_name) = Canal
      TEST @Value(igds_level_name) = Stream-riverside
      TEST @Value(igds_level_name) = Continuous line - solid line
      TEST @Value(igds_level_name) = Discontinous line - broken line
      TEST @Value(igds_level_name) = Railway line Train
      TEST @Value(igds_level_name) = Railway dock
      TEST @Value(igds_level_name) = Tram line
      TEST @Value(igds_level_name) = roadside
      TEST @Value(igds_level_name) = Lane-Footpath
      TEST @Value(igds_level_name) = Sidewalk
      TEST @Value(igds_level_name) = Cycling Path
      TEST @Value(igds_level_name) = Pedestrian Track",Line_features-not snapped
    Line_features-not snapped -> Chopper_2
TestFilter_32
    DEFAULT_VALUE = NON_POLYGON_Layers
    PASSED_TEST_GROUP_OUTPUT = FIRST
    TEST_LIST:
      "BOOL_OP,OR,COMPOSITE_TEST,""""""1 OR 2 OR 3 OR 4 OR 5 OR 6 OR 7 OR 8 OR 9"""""",TEST_CLAUSE,TEST @Value(igds_level_name) = Sports ground
      TEST @Value(igds_level_name) = Graveyard perimiter
      TEST @Value(igds_level_name) = Beach
      TEST @Value(igds_level_name) = Swamp
      TEST @Value(igds_level_name) = Pontoon
      TEST @Value(igds_level_name) = Parking area
      TEST @Value(igds_level_name) = Speed bump
      TEST @Value(igds_level_name) = Pedestrian crossing
      TEST @Value(igds_level_name) = Material_Direction_island",Polygon_features
    Polygon_features -> GeometryCoercer
GeometryCoercer
    GQUERY:
      for $geom in //geometry
      where $geom/count(parent::geometry) = 0
      return number($geom/@fme_id)
    KIND = fme_line
    COERCED -> Chopper_2
Chopper_2
    DEAGGREGATE_INPUT = Deaggregate
    MAX_VERTICES = 1
    MODE = By Vertex
    REMNANT_ATTR = _remnant
    CHOPPED -> AttributeCreator_29
AttributeCreator_29
    ATTR_TABLE:
      SET_TO Vertex_X = @XValue()
      SET_TO Vertex_Y = @YValue()
      SET_TO Vertex_Z = @ZValue()
    -> AttributeRounder_4
Note: Line-2d snap & near object issues
AttributeRounder_4
    PLACES = 4
    ROUND_TYPE = Nearest
    SRC_ATTRS = Vertex_Y Vertex_Z Vertex_X
    -> PointOnPointOverlayer_2 [POINT]
PointOnPointOverlayer_2
    ATTR_ACCUM_MODE = Prefix Incoming
    DEAGGREGATE_INPUT = Yes
    INCOMING_PREFIX = Near_
    LIST_ATTRS_TO_INCLUDE = Vertex_X Vertex_Y Vertex_Z
    LIST_NAME = Near_
    OV_ATTR = _overlaps
    TOLERANCE = 0.07
    POINT -> Tester_2
Tester_2
    BOOL_OP = OR
    TEST_CLAUSE = TEST @Value(_overlaps) = 0
    TEST_MODE = TEST
    FAILED -> TestFilter_21
TestFilter_21
    DEFAULT_VALUE = <UNFILTERED>
    PASSED_TEST_GROUP_OUTPUT = FIRST
    TEST_LIST:
      "BOOL_OP,AND,COMPOSITE_TEST,""""""1 AND 2 AND 3"""""",TEST_CLAUSE,TEST @Value(Vertex_X) = @Value(Near_{0}.Vertex_X)
      TEST @Value(Vertex_Y) = @Value(Near_{0}.Vertex_Y)
      TEST @Value(Vertex_Z) = @Value(Near_{0}.Vertex_Z)",3d-snapped,"BOOL_OP,AND,COMPOSITE_TEST,""""""1 AND 2 AND 3"""""",TEST_CLAUSE,TEST @Value(Vertex_X) = @Value(Near_{0}.Vertex_X)
      TEST @Value(Vertex_Y) = @Value(Near_{0}.Vertex_Y)
      TEST @Value(Vertex_Z) != @Value(Near_{0}.Vertex_Z)",2d-snapped
    2d-snapped -> AttributeCreator_31
    <UNFILTERED> -> AttributeCreator_30
AttributeCreator_31
    ATTR_TABLE = SET_TO Error_Level = CHK_2D Snapped here
AttributeCreator_30
    ATTR_TABLE = SET_TO Error_Level = CHK_Near-10CM_Object

Bookmark: New Bookmark
TestFilter_23
    DEFAULT_VALUE = <UNFILTERED>
    PASSED_TEST_GROUP_OUTPUT = FIRST
    TEST_LIST = "BOOL_OP,OR,COMPOSITE_TEST,""""""1"""""",TEST_CLAUSE,TEST @Value(igds_level_name) = roadside",Roadside
    Roadside -> SpatialRelator [Supplier]
Note: Missing roadside & meterial direction island check
TestFilter_22
    DEFAULT_VALUE = <UNFILTERED>
    PASSED_TEST_GROUP_OUTPUT = FIRST
    TEST_LIST = "BOOL_OP,OR,COMPOSITE_TEST,""""""1"""""",TEST_CLAUSE,TEST @Value(igds_level_name) = Material_Direction_island",Island
    Island -> SpatialRelator [Requestor]
    Island -> SpatialFilter_7 [Candidate]
SpatialRelator
    AGGREGATE_HANDLING = Yes
    CALC_CARD = No
    CURVE_BOUNDARY_RULE_PARAM = Default Rule
    PREDICATES = TOUCHES WITHIN EQUALS INTERSECTS CONTAINS
    SUCCESS_ATTR = _related_candidates
    -> Tester_5
Tester_5
    BOOL_OP = OR
    TEST_CLAUSE = TEST @Value(_related_candidates) = 0
    TEST_MODE = TEST
    FAILED -> SpatialFilter_7 [Filter]
SpatialFilter_7
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> AttributeCreator_23
AttributeCreator_23
    ATTR_TABLE = SET_TO Error_Level = Err_roadside-missing-in-Island
    -> AttributeCreator_7

Bookmark: New Bookmark
Junction_11
    -> TestFilter_26
    -> TestFilter_27
TestFilter_26
    DEFAULT_VALUE = Non-Line_Layers
    PASSED_TEST_GROUP_OUTPUT = FIRST
    TEST_LIST:
      "BOOL_OP,OR,COMPOSITE_TEST,""""""1 OR 2 OR 3 OR 4 OR 5 OR 6 OR 7 OR 8 OR 9 OR 10 OR 11 OR 12 OR 13 OR 14 OR 15 OR 16 OR 17 OR 18 OR 19 OR 20 OR 21 OR 22 OR 23 OR 24 OR 25 OR 26 OR 27 OR 28 OR 29 OR 30 OR 31 OR 32 OR 33 OR 34 OR 35 OR 36"""""",TEST_CLAUSE,TEST @Value(igds_level_name) = Paint marks on sports ground
      TEST @Value(igds_level_name) = Stairway
      TEST @Value(igds_level_name) = Fence
      TEST @Value(igds_level_name) = Wall (axis)
      TEST @Value(igds_level_name) = Portal
      TEST @Value(igds_level_name) = Retaining wall top
      TEST @Value(igds_level_name) = Retaining wall base
      TEST @Value(igds_level_name) = Coast line
      TEST @Value(igds_level_name) = Canal
      TEST @Value(igds_level_name) = Dock or river dock
      TEST @Value(igds_level_name) = Stream-riverside
      TEST @Value(igds_level_name) = Rock dyke
      TEST @Value(igds_level_name) = post line
      TEST @Value(igds_level_name) = Concrete dyke
      TEST @Value(igds_level_name) = Narrow-Ditch_Slope_top
      TEST @Value(igds_level_name) = Ordinary contours
      TEST @Value(igds_level_name) = Top of slope
      TEST @Value(igds_level_name) = Bottom of slope
      TEST @Value(igds_level_name) = Major contours
      TEST @Value(igds_level_name) = Rock area
      TEST @Value(igds_level_name) = Continuous line - solid line
      TEST @Value(igds_level_name) = Discontinous line - broken line
      TEST @Value(igds_level_name) = Railway line Train
      TEST @Value(igds_level_name) = Railway dock
      TEST @Value(igds_level_name) = Tram line
      TEST @Value(igds_level_name) = Vegetation alignment
      TEST @Value(igds_level_name) = Metal safety barrier
      TEST @Value(igds_level_name) = Concrete safety barrier
      TEST @Value(igds_level_name) = roadside
      TEST @Value(igds_level_name) = Pedestrian bridge
      TEST @Value(igds_level_name) = Lane-Footpath
      TEST @Value(igds_level_name) = Bridge
      TEST @Value(igds_level_name) = overpass
      TEST @Value(igds_level_name) = Cycling Path
      TEST @Value(igds_level_name) = Pedestrian Track
      TEST @Value(igds_level_name) = Big_Advertise_Signpost",Line_features
    Line_features -> LineOnAreaOverlayer_2 [LINE]
Junction_10
    -> LineOnAreaOverlayer_2 [AREA]
    -> GeometryCoercer_2
    -> SpatialFilter_6 [Filter]
    -> Junction_12
Note: Building & Other lines crossing errors
LineOnAreaOverlayer_2
    CLEANING_TOLERANCE = 0
    DEAGGREGATE_INPUT = Yes
    OVERLAY_TYPE = LINE_ON_AREA
    OV_ATTR = _overlaps
    LINE -> TestFilter_24
TestFilter_24
    DEFAULT_VALUE = <UNFILTERED>
    PASSED_TEST_GROUP_OUTPUT = FIRST
    TEST_LIST = "BOOL_OP,OR,COMPOSITE_TEST,""""""1"""""",TEST_CLAUSE,TEST @Value(_overlaps) = 0",@Value(_overlaps) = 0
    <UNFILTERED> -> AttributeCreator_25
AttributeCreator_25
    ATTR_TABLE = SET_TO Line_error = error
    -> Junction_14
Junction_14
    -> Chopper_4
    -> Chopper_5
Chopper_4
    DEAGGREGATE_INPUT = Deaggregate
    MAX_VERTICES = 2
    MODE = By Vertex
    REMNANT_ATTR = _remnant
    CHOPPED -> Chopper
    UNTOUCHED -> Chopper
Chopper
    DEAGGREGATE_INPUT = Deaggregate
    MAX_VERTICES = 2
    MODE = By Vertex
    REMNANT_ATTR = _remnant
    CHOPPED -> CenterPointReplacer
    UNTOUCHED -> CenterPointReplacer
CenterPointReplacer
    POINTTYPE = CENTEROFGRAV
    POINT -> Bufferer_3
Chopper_5
    DEAGGREGATE_INPUT = Deaggregate
    MAX_VERTICES = 1
    MODE = By Vertex
    REMNANT_ATTR = _remnant
    CHOPPED -> Matcher_2
Matcher_2
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = igds_element_id
    MATCH_STRATEGY = Match Selected Attributes
    SINGLE_MATCHED -> Bufferer_3
    NOT_MATCHED -> Bufferer_3
Bufferer_3
    ANGLE = 22.5
    CAP_STYLE = Round
    CORNER_STYLE = Round
    MODE = AREA
    OFFSET = 0.0001
    OFFSET_UNITS = NONE
    BUFFERED -> SpatialFilter_6 [Candidate]
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> AttributeCreator_26
AttributeCreator_26
    ATTR_TABLE = SET_TO Error_Level = Err_Building_Grop_Crossing
    -> AttributeCreator_7
GeometryCoercer_2
    GQUERY:
      for $geom in //geometry
      where $geom/count(parent::geometry) = 0
      return number($geom/@fme_id)
    KIND = fme_line

Bookmark: New Bookmark
TestFilter_27
    PASSED_TEST_GROUP_OUTPUT = FIRST
    TEST_LIST:
      "BOOL_OP,OR,COMPOSITE_TEST,""""""1 OR 2 OR 3 OR 4 OR 5 OR 6 OR 7 OR 8"""""",TEST_CLAUSE,TEST @Value(igds_level_name) = Stairway
      TEST @Value(igds_level_name) = Fence
      TEST @Value(igds_level_name) = Wall (axis)
      TEST @Value(igds_level_name) = Portal
      TEST @Value(igds_level_name) = Retaining wall top
      TEST @Value(igds_level_name) = Retaining wall base
      TEST @Value(igds_level_name) = Canal
      TEST @Value(igds_level_name) = Vegetation alignment",Line_features
    Line_features -> LineOnLineOverlayer_5 [LINE]
Note: Stair_Oerlap with building Polygons_ERRORS
Junction_12
    -> GeometryCoercer_3
GeometryCoercer_3
    GQUERY:
      for $geom in //geometry
      where $geom/count(parent::geometry) = 0
      return number($geom/@fme_id)
    KIND = fme_line
    COERCED -> LineOnLineOverlayer_5 [LINE]
LineOnLineOverlayer_5
    ATTRS_ACCUM_MODE = Use Attributes From One Feature
    CLEANING_TOLERANCE = 0
    DEAGGREGATE_INPUT = Yes
    GENERATE_LIST_DROP = YES
    LIST_ATTRS_TO_INCLUDE = igds_level_name
    LIST_NAME = _line
    OV_ATTR = Line_overlaps
    SEPARATE_COLLINEAR_SEGMENTS = Yes
    LINE -> Tester_9
Tester_9
    BOOL_OP = OR
    TEST_CLAUSE = TEST @Value(Line_overlaps) = 1
    TEST_MODE = TEST
    FAILED -> Tester_10
Tester_10
    BOOL_OP = OR
    TEST_CLAUSE = TEST @Value(igds_level_name) = Stairway
    TEST_MODE = TEST
    PASSED -> AttributeCreator_27
AttributeCreator_27
    ATTR_TABLE = SET_TO Error_Level = Err_Stairs_Overlap_with_Polygons
    -> AttributeCreator_7

Bookmark: New Bookmark
TestFilter_16
    DEFAULT_VALUE = <UNFILTERED>
    PASSED_TEST_GROUP_OUTPUT = FIRST
    TEST_LIST:
      "BOOL_OP,OR,COMPOSITE_TEST,""""""1 OR 2 OR 3 OR 4 OR 5 OR 6 OR 7"""""",TEST_CLAUSE,TEST @Value(igds_level_name) = Main Buildings
      TEST @Value(igds_level_name) = Other Buildings
      TEST @Value(igds_level_name) = Building in ruins
      TEST @Value(igds_level_name) = Wall
      TEST @Value(igds_level_name) = Border
      TEST @Value(igds_level_name) = Swimming Pool
      TEST @Value(igds_level_name) = Pond",polygons,"BOOL_OP,OR,COMPOSITE_TEST,""""""1 OR 2 OR 3 OR 4 OR 5 OR 6 OR 7 OR 8 OR 9"""""",TEST_CLAUSE,TEST @Value(igds_level_name) = Wall (axis)
      TEST @Value(igds_level_name) = Portal
      TEST @Value(igds_level_name) = Retaining wall top
      TEST @Value(igds_level_name) = Retaining wall base
      TEST @Value(igds_level_name) = Fence
      TEST @Value(igds_level_name) = Vegetation alignment
      TEST @Value(igds_level_name) = Stairway
      TEST @Value(igds_level_name) = roadside
      TEST @Value(igds_level_name) = Lane-Footpath",lines
    polygons -> LineOnAreaOverlayer [AREA]
    lines -> LineOnAreaOverlayer [LINE]
LineOnAreaOverlayer
    ATTR_ACCUM_MODE = Merge Incoming
    ATTR_CONFLICT_RES = Use Original
    CANDIDATE_LIST_ATTRS_TO_INCLUDE = igds_level_name OBJ_ID
    CANDIDATE_LIST_ATTRS_TO_INCLUDE_MODE = Selected Attributes
    CANDIDATE_LIST_NAME = Area
    CLEANING_TOLERANCE = None
    DEAGGREGATE_INPUT = Yes
    LIST_ATTRS_TO_INCLUDE = igds_level_name OBJ_ID
    LIST_NAME = line
    OVERLAY_TYPE = LINE_ON_AREA
    OV_ATTR = _overlaps
    LINE -> Counter_2
    AREA -> TestFilter_17
Counter_2
    CNT_ATTR = Line_Count
    DOMAIN = counter
    SCOPE = Global
    START = 1
    -> Snipper
Snipper
    DEAGGREGATE_INPUT = YES
    ENDLOCATIONATTR = 99.999
    MEASUREMENTTYPE = 2D
    SNIPMODE = Distance (Percentage)
    STARTLOCATIONATTR = 0.0001
    -> SpatialFilter_4 [Candidate]
TestFilter_17
    DEFAULT_VALUE = <UNFILTERED>
    PASSED_TEST_GROUP_OUTPUT = FIRST
    TEST_LIST = "BOOL_OP,OR,COMPOSITE_TEST,""""""1"""""",TEST_CLAUSE,TEST @Value(_overlaps) <= 1",no errors
    <UNFILTERED> -> SpatialFilter_4 [Filter]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> AttributeCreator_18
Note: Line-Inside polygons errors
AttributeCreator_18
    ATTR_TABLE = SET_TO Error_Level = Err_Line_inside_Polygon
    -> AttributeCreator_7

Bookmark: POLYGONS-WRONG-DIRECTIONS
OrientationExtractor
    ORIENTATION = _orientation
    -> TestFilter_13
TestFilter_13
    DEFAULT_VALUE = <UNFILTERED>
    PASSED_TEST_GROUP_OUTPUT = FIRST
    TEST_LIST = "BOOL_OP,OR,COMPOSITE_TEST,""""""1"""""",TEST_CLAUSE,TEST @Value(_orientation) = right_hand_rule",Wrong_Geometry-Polygons
    Wrong_Geometry-Polygons -> AttributeCreator_22
AttributeCreator_22
    ATTR_TABLE = SET_TO Error_Level = Err_Wrong_Direction_polygon
    -> AttributeCreator_7

Bookmark: AREA Overalp - polygons
TestFilter_15
    DEFAULT_VALUE = <UNFILTERED>
    PASSED_TEST_GROUP_OUTPUT = FIRST
    TEST_LIST:
      "BOOL_OP,OR,COMPOSITE_TEST,""""""1 OR 2 OR 3 OR 4 OR 5 OR 6 OR 7 OR 8 OR 9 OR 10 OR 11 OR 12 OR 13 OR 14 OR 15 OR 16 OR 17 OR 18"""""",TEST_CLAUSE,TEST @Value(igds_level_name) = Sports ground
      TEST @Value(igds_level_name) = Other Buildings
      TEST @Value(igds_level_name) = Graveyard perimiter
      TEST @Value(igds_level_name) = Main Buildings
      TEST @Value(igds_level_name) = Flagstone-terrace
      TEST @Value(igds_level_name) = Greenhouse
      TEST @Value(igds_level_name) = Wall
      TEST @Value(igds_level_name) = Building in ruins
      TEST @Value(igds_level_name) = Pond
      TEST @Value(igds_level_name) = Beach
      TEST @Value(igds_level_name) = Swimming Pool
      TEST @Value(igds_level_name) = Swamp
      TEST @Value(igds_level_name) = Pontoon
      TEST @Value(igds_level_name) = DAM
      TEST @Value(igds_level_name) = Reservoir-Silo
      TEST @Value(igds_level_name) = Parking area
      TEST @Value(igds_level_name) = Speed bump
      TEST @Value(igds_level_name) = Pedestrian crossing",Poly
    Poly -> Counter_5
Counter_5
    CNT_ATTR = Input_ID
    DOMAIN = Input_ID
    SCOPE = Global
    START = 1
    -> AreaCalculator_4
AreaCalculator_4
    AREA_ATTR = IN_POLY_Size
    AREA_TYPE = Plane Area
    MULT = 1
    -> Junction_4
    -> AreaOnAreaOverlayer_3 [AREA]
    -> SpatialFilter_9 [Filter]
Junction_4
    -> Chopper_3
Chopper_3
    DEAGGREGATE_INPUT = Deaggregate
    MAX_VERTICES = 1
    MODE = By Vertex
    REMNANT_ATTR = _remnant
    CHOPPED -> Matcher
Matcher
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = igds_element_id
    MATCH_STRATEGY = Match Selected Attributes
    SINGLE_MATCHED -> AttributeCreator
    NOT_MATCHED -> AttributeCreator
AreaOnAreaOverlayer_3
    ACCUM_ATTRS_NAME = Use Attributes From One Feature
    CLEANING_TOLERANCE = 0
    CONNECT_Z_MODE = First Wins
    DEAGGREGATE_INPUT = Yes
    LIST_ATTRS_TO_INCLUDE = igds_level_name IN_POLY_Size OBJ_ID
    LIST_NAME = Area_
    OVC_ATTR = Area_overlaps
    AREA -> TestFilter_28
TestFilter_28
    DEFAULT_VALUE = <UNFILTERED>
    PASSED_TEST_GROUP_OUTPUT = FIRST
    TEST_LIST = "BOOL_OP,OR,COMPOSITE_TEST,""""""1"""""",TEST_CLAUSE,TEST @Value(Area_overlaps) = 1",@Value(Area_overlaps) = 1
    <UNFILTERED> -> DonutHoleExtractor_3
DonutHoleExtractor_3
    DEAGGREGATE_INPUT = Yes
    OUTERSHELL -> SpatialFilter_9 [Candidate]
    HOLE -> SpatialFilter_9 [Candidate]
SpatialFilter_9
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = EQUALS
    USE_BOUNDING_BOX = No
    FAILED -> 2DForcer_4
2DForcer_4
    2D -> AreaCalculator_9
AreaCalculator_9
    AREA_ATTR = Out_area
    AREA_TYPE = Plane Area
    MULT = 1
    -> AttributeRounder_10
AttributeRounder_10
    PLACES = 6
    ROUND_TYPE = Nearest
    SRC_ATTRS = IN_POLY_Size Out_area
    -> TestFilter_31
Note: AREA - Overlap - Polygons
TestFilter_31
    DEFAULT_VALUE = <UNFILTERED>
    PASSED_TEST_GROUP_OUTPUT = FIRST
    TEST_LIST = "BOOL_OP,OR,COMPOSITE_TEST,""""""1"""""",TEST_CLAUSE,TEST @Value(Out_area) = 0",0-size poly,"BOOL_OP,OR,COMPOSITE_TEST,""""""1"""""",TEST_CLAUSE,TEST @Value(IN_POLY_Size) = @Value(Out_area)",Same-Size
    <UNFILTERED> -> AttributeCreator_24
AttributeCreator_24
    ATTR_TABLE = SET_TO Error_Level = Err_Overlap Polygons
    -> AttributeCreator_7

Bookmark: Near 10CM vertex - in the objects
AttributeCreator
    ATTR_TABLE:
      SET_TO Vertex_X = @XValue()
      SET_TO Vertex_Y = @YValue()
      SET_TO Vertex_Z = @ZValue()
    -> AttributeRounder_3
AttributeRounder_3
    PLACES = 4
    ROUND_TYPE = Nearest
    SRC_ATTRS = Vertex_Y Vertex_Z Vertex_X
    -> PointOnPointOverlayer [POINT]
PointOnPointOverlayer
    ATTR_ACCUM_MODE = Prefix Incoming
    DEAGGREGATE_INPUT = Yes
    INCOMING_PREFIX = Near_
    LIST_ATTRS_TO_INCLUDE = Vertex_X Vertex_Y Vertex_Z
    LIST_NAME = Near_
    OV_ATTR = _overlaps
    TOLERANCE = 0.07
    POINT -> Tester_4
Tester_4
    BOOL_OP = OR
    TEST_CLAUSE = TEST @Value(_overlaps) = 0
    TEST_MODE = TEST
    FAILED -> TestFilter_20
TestFilter_20
    DEFAULT_VALUE = <UNFILTERED>
    PASSED_TEST_GROUP_OUTPUT = FIRST
    TEST_LIST:
      "BOOL_OP,AND,COMPOSITE_TEST,""""""1 AND 2 AND 3"""""",TEST_CLAUSE,TEST @Value(Vertex_X) = @Value(Near_{0}.Vertex_X)
      TEST @Value(Vertex_Y) = @Value(Near_{0}.Vertex_Y)
      TEST @Value(Vertex_Z) = @Value(Near_{0}.Vertex_Z)",3d-snapped,"BOOL_OP,AND,COMPOSITE_TEST,""""""1 AND 2 AND 3"""""",TEST_CLAUSE,TEST @Value(Vertex_X) = @Value(Near_{0}.Vertex_X)
      TEST @Value(Vertex_Y) = @Value(Near_{0}.Vertex_Y)
      TEST @Value(Vertex_Z) != @Value(Near_{0}.Vertex_Z)",2d-snapped
    <UNFILTERED> -> AttributeCreator_28
AttributeCreator_28
    ATTR_TABLE = SET_TO Error_Level = CHK_Near-10CM_Object
    -> AttributeCreator_7

Bookmark: For BUILDING & ROOF_SNAP_ERRORS
TestFilter_6
    DEFAULT_VALUE = <UNFILTERED>
    PASSED_TEST_GROUP_OUTPUT = FIRST
    TEST_LIST:
      "BOOL_OP,OR,COMPOSITE_TEST,""""""1 OR 2 OR 3 OR 4"""""",TEST_CLAUSE,TEST @Value(igds_level_name) = Main Buildings
      TEST @Value(igds_level_name) = Other Buildings
      TEST @Value(igds_level_name) = Greenhouse
      TEST @Value(igds_level_name) = Building in ruins",BUILDING_POLYGONS,"BOOL_OP,OR,COMPOSITE_TEST,""""""1"""""",TEST_CLAUSE,TEST @Value(igds_level_name) = Roof ridge",ROOF_RIDGE
    BUILDING_POLYGONS -> Counter_3
    BUILDING_POLYGONS -> Junction_10
    ROOF_RIDGE -> Counter_4
Note: FOR OTHER LOGICAL_CHECKS
Counter_3
    CNT_ATTR = Build_Poly_ID
    DOMAIN = Build_Poly_ID
    SCOPE = Global
    START = 1
    -> Bufferer_2
    -> VertexExtractor-POLYGON
Bufferer_2
    ANGLE = 22.5
    CAP_STYLE = Round
    CORNER_STYLE = Round
    MODE = AREA
    OFFSET = 0.01
    OFFSET_UNITS = NONE
    BUFFERED -> SpatialFilter_5 [Filter]
VertexExtractor-POLYGON
    Point -> AttributeRenamer_2
AttributeRenamer_2
    ATTR_TABLE:
      RENAME_SET_DEFAULT _x > Polygon_X
      RENAME_SET_DEFAULT _y > Polygon_Y
      RENAME_SET_DEFAULT _z > Polygon_Z
    -> VertexCounter_2
VertexCounter_2
    CNT_ATTR = _coordcount
    -> VertexRemover
VertexRemover
    IND = @Value(_vertex_number)
    KEEP_REMOVE_PARAM = Keep
    LEN = 0
    <REJECTED> -> AttributeRounder
AttributeRounder
    PLACES = 4
    ROUND_TYPE = Nearest
    SRC_ATTRS = Polygon_X Polygon_Y Polygon_Z
    -> AttributeConcatenator_5
AttributeConcatenator_5
    ATTRS = Polygon_Y Polygon_X
    CASE = No
    DEST_ATTR = Polygon_XYZ
    DROP_EMPTY_PARTS = No
    ORDER = NameDescending
    SEP = ,
    TRIM_OPTION = None
    -> AttributeConcatenator_4
AttributeConcatenator_4
    ATTRS = Polygon_Y Polygon_X
    CASE = No
    DEST_ATTR = Polygon_XY
    DROP_EMPTY_PARTS = No
    ORDER = NameDescending
    SEP = ,
    TRIM_OPTION = None
    -> FeatureMerger [SUPPLIER]
Counter_4
    CNT_ATTR = Roof_ID
    DOMAIN = Roof_ID
    SCOPE = Global
    START = 1
    -> SpatialFilter_5 [Candidate]
SpatialFilter_5
    AGGREGATE_HANDLING = Yes
    ATTR_ACCUM_MODE = Prefix Filter
    ATTR_PREFIX = _Merge_ID
    BASE_TYPE = Multiple Filters
    CURVE_BOUNDARY_RULE_PARAM = Default Rule
    PASS_CRITERIA = Pass Against One Filter
    PREDATTR = _predicate
    PREDICATES = CONTAINS
    USE_BOUNDING_BOX = No
    PASSED -> VertexExtractor-ROOF
    FAILED -> AttributeCreator_11
VertexExtractor-ROOF
    Point -> AttributeRenamer
AttributeRenamer
    ATTR_TABLE:
      RENAME_SET_DEFAULT _x > ROOF_X
      RENAME_SET_DEFAULT _y > ROOF_Y
      RENAME_SET_DEFAULT _z > ROOF_Z
    -> AttributeRounder_2
AttributeRounder_2
    PLACES = 4
    ROUND_TYPE = Nearest
    SRC_ATTRS = ROOF_Z ROOF_Y ROOF_X
    -> AttributeConcatenator_2
AttributeConcatenator_2
    ATTRS = ROOF_X ROOF_Z ROOF_Y
    CASE = No
    DEST_ATTR = Roof_XYZ
    DROP_EMPTY_PARTS = No
    ORDER = NameDescending
    SEP = ,
    TRIM_OPTION = None
    -> AttributeConcatenator_3
AttributeConcatenator_3
    ATTRS = ROOF_X ROOF_Y
    CASE = No
    DEST_ATTR = Roof_XY
    DROP_EMPTY_PARTS = No
    ORDER = NameDescending
    SEP = ,
    TRIM_OPTION = None
    -> FeatureMerger [REQUESTOR]
FeatureMerger
    ATTR_ACCUM_MODE = Merge Supplier
    ATTR_CONFLICT_RES = Use Requestor
    IGNORE_NULLS = No
    JOIN_KEYS = @Value(Roof_XY) @Value(Polygon_XY) AUTO
    LIST_ATTRS_TO_INCLUDE = Polygon_X Polygon_Y Polygon_Z Build_Poly_ID
    LIST_NAME = Merged
    MERGE_TYPE = Attributes Only
    PROCESS_DUPS = NO
    REJECT_NULL_MISSING_KEYS = No
    SUPPLIERS_FIRST = No
    MERGED -> TestFilter_12
TestFilter_12
    DEFAULT_VALUE = <UNFILTERED>
    PASSED_TEST_GROUP_OUTPUT = FIRST
    TEST_LIST:
      "BOOL_OP,AND,COMPOSITE_TEST,""""""1 AND 2"""""",TEST_CLAUSE,TEST @Value(Polygon_Z) = @Value(ROOF_Z)
      TEST @Value(Build_Poly_ID) = @Value(_Merge_IDBuild_Poly_ID)",3D_Snapped,"BOOL_OP,AND,COMPOSITE_TEST,""""""1 AND 2"""""",TEST_CLAUSE,TEST @Value(Polygon_Z) != @Value(ROOF_Z)
      TEST @Value(Build_Poly_ID) = @Value(_Merge_IDBuild_Poly_ID)",2D_Snapped
    2D_Snapped -> AttributeCreator_12
AttributeCreator_12
    ATTR_TABLE = SET_TO Error_Level = Err_Roof_ridge_Building_Snap_issues_CHK
    -> Junction_7
AttributeCreator_11
    ATTR_TABLE = SET_TO Error_Level = Err_Roof_ridge_not_Line or Outside Building
    -> Junction_7
Junction_7
    -> AttributeCreator_7

Bookmark: ALTIMETRIC_POINTS_CHECK
TestFilter_10
    DEFAULT_VALUE = <UNFILTERED>
    PASSED_TEST_GROUP_OUTPUT = FIRST
    TEST_LIST:
      "BOOL_OP,OR,COMPOSITE_TEST,""""""1"""""",TEST_CLAUSE,TEST @Value(igds_level_name) = Speed bump",Speed bump,"BOOL_OP,OR,COMPOSITE_TEST,""""""1"""""",TEST_CLAUSE,TEST @Value(igds_level_name) = Portal",Portal,"BOOL_OP,OR,COMPOSITE_TEST,""""""1 OR 2 OR 3 OR 4 OR 5 OR 6 OR 7 OR 8 OR 9"""""",TEST_CLAUSE,TEST @Value(igds_level_name) = Main Buildings
      TEST @Value(igds_level_name) = Other Buildings
      TEST @Value(igds_level_name) = Greenhouse
      TEST @Value(igds_level_name) = Building in ruins
      TEST @Value(igds_level_name) = Pond
      TEST @Value(igds_level_name) = Swimming Pool
      TEST @Value(igds_level_name) = Wall
      TEST @Value(igds_level_name) = DAM
      TEST @Value(igds_level_name) = Flagstone-terrace",For_Buil_POLYGON_GROUPS,"BOOL_OP,OR,COMPOSITE_TEST,""""""1 OR 2"""""",TEST_CLAUSE,TEST @Value(igds_level_name) = Altimetric point
      TEST @Value(igds_level_name) = Altimetric point crossroads axis",FOR_ALTI_POINTS,"BOOL_OP,OR,COMPOSITE_TEST,""""""1 OR 2 OR 3 OR 4"""""",TEST_CLAUSE,TEST @Value(igds_level_name) = Brushwood
      TEST @Value(igds_level_name) = Wood
      TEST @Value(igds_level_name) = Grass
      TEST @Value(igds_level_name) = Cultivation_area",For_Vegetation
    Speed bump -> SpatialFilter [Filter]
    Portal -> SpatialFilter [Candidate]
    For_Buil_POLYGON_GROUPS -> SpatialFilter_2 [Filter]
    FOR_ALTI_POINTS -> SpatialFilter_2 [Candidate]
    For_Vegetation -> AreaOnAreaOverlayer [AREA]
    For_Vegetation -> SpatialFilter_3 [Filter]
AreaOnAreaOverlayer
    ACCUM_ATTRS_NAME = Use Attributes From One Feature
    CLEANING_TOLERANCE = Automatic
    CONNECT_Z_MODE = First Wins
    DEAGGREGATE_INPUT = Yes
    OVC_ATTR = _overlaps
    AREA -> SpatialFilter_3 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    GROUP_BY = igds_level_name
    PASS_CRITERIA = Pass Against One Filter
    PREDATTR = Overlap_Status
    PREDICATES = INTERSECTS
    USE_BOUNDING_BOX = No
    PASSED -> TestFilter_11
TestFilter_11
    DEFAULT_VALUE = <UNFILTERED>
    PASSED_TEST_GROUP_OUTPUT = FIRST
    TEST_LIST = "BOOL_OP,OR,COMPOSITE_TEST,""""""1"""""",TEST_CLAUSE,TEST @Value(_overlaps) = 2",@Value(_overlaps) = 2
    @Value(_overlaps) = 2 -> AttributeCreator_10
AttributeCreator_10
    ATTR_TABLE = SET_TO Error_Level = Err_Vegetation_poly_Overlap_Not_allowed
    -> Junction_6
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS INTERSECTS
    USE_BOUNDING_BOX = No
    PASSED -> AttributeCreator_8
AttributeCreator_8
    ATTR_TABLE = SET_TO Error_Level = Err_Speed-bump
    -> Junction_6
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS INTERSECTS TOUCHES
    USE_BOUNDING_BOX = No
    PASSED -> AttributeCreator_9
AttributeCreator_9
    ATTR_TABLE = SET_TO Error_Level = CHECK_Alti_point_inside_Polygons
    -> Junction_6
Junction_6
    -> AttributeCreator_7

Bookmark: VERTEX COUNT CHECK
TestFilter_5_-VERTEX_COUNT_CHECK
    DEFAULT_VALUE = <UNFILTERED>
    PASSED_TEST_GROUP_OUTPUT = FIRST
    TEST_LIST:
      "BOOL_OP,OR,COMPOSITE_TEST,""""""1 OR 2 OR 3"""""",TEST_CLAUSE,TEST @Value(igds_level_name) = Portal
      TEST @Value(igds_level_name) = Roof ridge
      TEST @Value(igds_level_name) = Speed bump",@Value(igds_level_name) = Portal
    @Value(igds_level_name) = Portal -> VertexCounter
VertexCounter
    CNT_ATTR = Vertex_Count
    -> TestFilter_5
TestFilter_5
    DEFAULT_VALUE = error-in-vertex-count
    PASSED_TEST_GROUP_OUTPUT = FIRST
    TEST_LIST:
      "BOOL_OP,AND,COMPOSITE_TEST,""""""1 AND 2"""""",TEST_CLAUSE,TEST @Value(igds_level_name) = Portal
      TEST @Value(Vertex_Count) = 2",@Value(igds_level_name)=Portal
      @Value(Vertex_Count)=2 = Vertex_Count_Correct,"BOOL_OP,AND,COMPOSITE_TEST,""""""1 AND 2"""""",TEST_CLAUSE,TEST @Value(igds_level_name) = Speed bump
      TEST @Value(Vertex_Count) = 5",@Value(igds_level_name)=Portal
      @Value(Vertex_Count)=2 = Vertex_Count_Correct,"BOOL_OP,OR,COMPOSITE_TEST,""""""1 OR 2"""""",TEST_CLAUSE,TEST @Value(igds_level_name) = Roof ridge
      TEST @Value(Vertex_Count) = 2",@Value(igds_level_name)=Portal
      @Value(Vertex_Count)=2 = Vertex_Count_Correct
    error-in-vertex-count -> AttributeCreator_13
AttributeCreator_13
    ATTR_TABLE = SET_TO Error_Level = Err_Vertex_Count_Mismatch
    -> Junction_8

Bookmark: FOR SWIM_POOLS & Pond SAME HEIGHT CHECK
TestFilter_7
    DEFAULT_VALUE = <UNFILTERED>
    PASSED_TEST_GROUP_OUTPUT = FIRST
    TEST_LIST:
      "BOOL_OP,OR,COMPOSITE_TEST,""""""1 OR 2"""""",TEST_CLAUSE,TEST @Value(igds_level_name) = Swimming Pool
      TEST @Value(igds_level_name) = Pond",Swimimg-pool_Equal_height
    Swimimg-pool_Equal_height -> GeometryValidator_2
GeometryValidator_2
    ISSUE_ATTR_NAME = NON_planar_Swimpool
    PRESETS = Custom
    REPAIR = No
    RULES = PLANAR_SURFACE CHECK_AREA]DO_CHECK_AREA]TOLERANCE_MODE]AUTO]TOLERANCE]<Unused>]ANGULAR_TOLERANCE_MODE]IGNORE]ANGULAR_TOLERANCE]<Unused>]FME_CONTROLLER_QUERY_FILE]transformers/dependencies/geometryvalidator/PLANAR_SURFACE.fme
    SUMMARY = Detailed
    FAILED -> AttributeCreator_14
AttributeCreator_14
    ATTR_TABLE = SET_TO Error_Level = Err_Not_Same_Height
    -> Junction_8

Bookmark: Error_Output
Note: Error_Output
AttributeCreator_7
    ATTR_TABLE = SET_TO igds_level_name = @Value(Error_Level)_@Value(igds_level_name)
    -> Level1 (writer DGNV8_2)
Level1 (writer DGNV8_2)

FME custom transformer AttributeConcatenator
Concatenates selected attribute values in the order specified to the "Concatenating Order" parameter.
Resulting string consists of the original attribute values delimited by identical string specified to the "Separator String" parameter.
This transformer considers both Null value and Missing attribute as an empty string. 
See also the AttributeListPopulator.
Parameters
Attributes to Concatenate:
Select attributes which should be concatenated.
Concatenating Order:
Choose one of these as the concatenating order.
- Value Numeric Ascending: sorted by attribute value numeric ascending
- Value Numeric Descending: sorted by attribute value numeric descending
- Value Alphabetic Ascending: sorted by attribute value alphabetic ascending
- Value Alphabetic Descending: sorted by attribute value alphabetic descending
- Name Ascending (Alphabetic): sorted by attribute name alphabetic ascending
- Name Descending (Alphabetic): sorted by attribute name alphabetic descending
Note:
In "Value Numeric Ascending/Descending", the transformer considers every non-numeric value (including empty/null/missing) as 0.
But a numeric representation surrounded by white spaces will be treated as a numeric value (both leading and trailing white spaces will be ignored).
And leading 0 of a numeric representation will also be ignored when comparing it as a numeric value to other values.
Case Sensitive:
Yes: The transformer will perform case-sensitive sorting.
No (default): The transformer will perform case-insensitive sorting.
Note
The "Case Sensitive" parameter setting is basically applied to alphabetic sorting, but it will also be applied to non-numeric parts in numeric sorting, if non-numeric values exist.
Separator String:
Specify a string that will be used as the delimiter. You can set blank to this parameter not to use delimiter.
Trim Whitespaces:
By default, the transformer will remove Both leading and trailing whitespaces from every original attribute value before concatenating, but you can change the setting to either Left or Right, or None.
Destination Attribute:
Specify name of the attribute that stores the resulting string.
Drop Empty Parts:
Yes: The concatenation will be performed excluding empty parts.
No (default): The concatenation will be performed including empty parts.

Parameters:
- ATTRS =   # " " Attributes to Concatenate
- ORDER = ValueNumericAscending
- CASE = No   # Case Sensitive
- SEP = ,   # Separator String
- TRIM_OPTION = Both   # Trim Whitespaces
- DEST_ATTR = _concatenated   # TYPE:varchar(200) Destination Attribute
- DROP_EMPTY_PARTS = No   # Drop Empty Parts

Input (input)
    -> ParameterFetcher
ParameterFetcher
    ATTR_LIST = attributeconcatenator.attrs {$(ATTRS)} attributeconcatenator.sep {$(SEP)} attributeconcatenator.order {$(ORDER)} attributeconcatenator.case {$(CASE)} attributeconcatenator.trim_option {$(TRIM_OPTION)} attributeconcatenator.drop_empty {$(DROP_EMPTY_PARTS)}
    -> TclCaller
TclCaller
    SRC:
      proc concatAttrs {} {
          set attrs [FME_GetAttribute "attributeconcatenator.attrs"];
          set order [FME_GetAttribute "attributeconcatenator.order"];
          set nocase [string equal [FME_GetAttribute "attributeconcatenator.case"] {No}];
          set trimOption [FME_GetAttribute "attributeconcatenator.trim_option"];
          set trimOption [string map {Both trim Left trimleft Right trimright None ""} $trimOption];
          set keepEmpty [string equal [FME_GetAttribute "attributeconcatenator.drop_empty"] {No}];
          set sorted {};
          proc getAttr {name trimOption} {
              if {[string equal $trimOption {}]} {
                  return [FME_GetAttribute $name];
              } else {
                  return [string $trimOption [FME_GetAttribute $name]];
              };
          };
          if {[regexp {^ValueNumeric.+} $order]} {
              set num {}; set nan {};
              foreach name $attrs {
                  set v [getAttr $name $trimOption];
                  if {$keepEmpty || ![string equal $v {}]} {
                      set t [string trim $v]
                      set n [string trimleft [string range $t 0 end-1] {0}][string index $t end];
                      if {[string is double -strict $n]} {
                          lappend num [list $n $v];
                      } else {
                          lappend nan [list {0} $v];
                      };
                  };
              };
              if {$nocase} {
                  set nan [lsort -nocase -index 1 $nan];
              } else {
                  set nan [lsort -index 1 $nan];
              };
              foreach vv [lsort -real -index 0 [concat $nan $num]] {
                  lappend sorted [lindex $vv 1];
              };
          } elseif {[regexp {^ValueAlphabetic.+} $order]} {
              foreach name $attrs {
                  set v [getAttr $name $trimOption];
                  if {$keepEmpty || ![string equal $v {}]} {
                      lappend sorted $v;
                  };
              };
              if {$nocase} {
                  set sorted [lsort -nocase $sorted];
              } else {
                  set sorted [lsort $sorted];
              };
          } elseif {[regexp {^Name.+} $order]} {
              if {$nocase} {
                  set attrs [lsort -nocase $attrs];
              } else {
                  set attrs [lsort $attrs];
              };
              foreach name $attrs {
                  set v [getAttr $name $trimOption];
                  if {$keepEmpty || ![string equal $v {}]} {
                      lappend sorted $v;
                  };
              };
          } else {
              return "Debug: Invalid Concatenation Order: $order";
          };
          set delim [FME_GetAttribute "attributeconcatenator.sep"];
          if {[regexp {.+Ascending$} $order]} {
              return [join $sorted $delim];
          } elseif {[regexp {.+Descending$} $order]} {
              return [join [lreverse $sorted] $delim];
          } else {
              return "Debug: Invalid Concatenation Order: $order";
          };
      }
    TCLPROG = concatAttrs
    VAL_ATTR = attributeconcatenator.dest_attr
    -> BulkAttributeRenamer
BulkAttributeRenamer
    ATTRCHOICE = Selected Attributes
    ATTRLIST = attributeconcatenator.dest_attr
    PATTERN_ACTION_DISP = Regular Expression Replace
    REPLACE_PATTERN = .+
    REPLACE_STR = $(DEST_ATTR)
    -> BulkAttributeRemover
BulkAttributeRemover
    ATTR_EXP = ^attributeconcatenator.+
    -> Output (output)
Output (output)
